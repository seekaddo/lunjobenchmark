NR-UE-Variables DEFINITIONS AUTOMATIC TAGS ::= BEGIN

IMPORTS

AreaConfiguration-r17, ARFCN-ValueNR, CellIdentity, EUTRA-PhysCellId, 
   maxCEFReport-r17, maxCellReport, MeasId, MeasIdToAddModList, 
   MeasIdleCarrierEUTRA-r16, MeasIdleCarrierNR-r16, MeasResultIdleEUTRA-r16, 
   MeasResultIdleNR-r16, MeasReselectionCarrierNR-r18, 
   MeasurementValidityDuration-r18, MeasObjectToAddModList, 
   MeasConfigAppLayerId-r17, MeasConfigAppLayer-r17, maxNrofAppLayerMeas-r17, 
   AppLayerIdleInactiveConfig-r18, PhysCellId, RNTI-Value, 
   ReportConfigToAddModList, RSRP-Range, SL-MeasId-r16, SL-MeasIdList-r16, 
   SL-MeasObjectList-r16, SL-ReportConfigList-r16, SL-QuantityConfig-r16, 
   Tx-PoolMeasList-r16, QuantityConfig, maxNrofCellMeas, maxNrofMeasId, 
   maxFreqIdle-r16, PhysCellIdUTRA-FDD-r16, ValidityAreaList-r16, 
   CondReconfigToAddModList-r16, ConnEstFailReport-r16, LoggingDuration-r16, 
   LoggingInterval-r16, LogMeasInfoList-r16, LogMeasInfo-r16, RA-Report-r16, 
   RLF-Report-r16, TraceReference-r16, WLAN-Identifiers-r16, WLAN-NameList-r16
   , BT-NameList-r16, PLMN-Identity, maxNrofRelayMeas-r17, maxPLMN, 
   RA-ReportList-r16, VisitedCellInfoList-r16, AbsoluteTimeInfo-r16, 
   LoggedEventTriggerConfig-r16, LoggedPeriodicalReportConfig-r16, 
   Sensor-NameList-r16, SL-SourceIdentity-r17, SuccessHO-Report-r17, 
   PLMN-IdentityList2-r16, AreaConfiguration-r16, maxNrofSL-MeasId-r16, 
   maxNrofFreqSL-r16, maxNrofCLI-RSSI-Resources-r16, 
   maxNrofCLI-SRS-Resources-r16, RSSI-ResourceId-r16, SRS-ResourceId, 
   VisitedPSCellInfoList-r17, SuccessPSCell-Report-r18, maxNPN-r16, 
   SNPN-ConfigID-List-r18, AreaConfiguration-v1800, NID-r16, 
   SK-CounterConfig-r18, ReferenceConfiguration-r18, 
   maxNrofLTM-Configs-plus1-r18, maxSecurityCellSet-r18
FROM NR-RRC-Definitions ;

-- Productions

-- TAG-VARMEASRESELECTIONCONFIG-STOP
-- TAG-VARMOBILITYHISTORYREPORT-START
VarMobilityHistoryReport-r16 ::= VisitedCellInfoList-r16

VarAppLayerIdle-r18 ::= SEQUENCE {
   measConfigAppLayerId-r18 [0] MeasConfigAppLayerId-r17,
   serviceType-r18 [1] ENUMERATED { streaming(0), mtsi(1), vr(2), spare5(3), 
      spare4(4), spare3(5), spare2(6), spare1(7) },
   appLayerIdleInactiveConfig-r18 [2] AppLayerIdleInactiveConfig-r18,
   appLayerMeasPriority-r18 [3] INTEGER (1..16) OPTIONAL
}

-- NR-UE-VARIABLES-STOP
-- TAG-VARAPPLAYERIDLECONFIG-START
VarAppLayerIdleConfig-r18 ::= SEQUENCE {
   appLayerIdleConfigList-r18 [0] SEQUENCE (SIZE (1..maxNrofAppLayerMeas-r17)) OF VarAppLayerIdle-r18
}

VarAppLayerPLMN-List-r18 ::= SEQUENCE {
   measConfigAppLayerId-r18 [0] MeasConfigAppLayerId-r17,
   plmn-IdentityList-r18 [1] PLMN-IdentityList2-r16
}

-- TAG-VARAPPLAYERIDLECONFIG-STOP
-- TAG-VARAPPLAYERPLMN-LISTCONFIG-START
VarAppLayerPLMN-ListConfig-r18 ::= SEQUENCE {
   plmnConfigList-r18 [0] SEQUENCE (SIZE (1..maxNrofAppLayerMeas-r17)) OF VarAppLayerPLMN-List-r18
}

-- TAG-VARAPPLAYERPLMN-LISTCONFIG-STOP
-- TAG-VARCONDITIONALRECONFIG-START
VarConditionalReconfig ::= SEQUENCE {
   condReconfigList [0] CondReconfigToAddModList-r16 OPTIONAL,
   scpac-ReferenceConfiguration-r18 [1] ReferenceConfiguration-r18 OPTIONAL,
   sk-CounterConfiguration-r18 [2] SEQUENCE (SIZE (1..maxSecurityCellSet-r18)) OF SK-CounterConfig-r18
       OPTIONAL
}

SNPN-Identity-r18 ::= SEQUENCE {
   plmn-Identity-r18 [0] PLMN-Identity,
   nid-r18 [1] NID-r16
}

-- TAG-VARCONDITIONALRECONFIG-STOP
-- TAG-VARCONNESTFAILREPORT-START
VarConnEstFailReport-r16 ::= SEQUENCE {
   connEstFailReport-r16 [0] ConnEstFailReport-r16,
   networkIdentity-r18 [1] EXPLICIT CHOICE {
      plmn-Identity-r18 [0] PLMN-Identity,
      snpn-Identity-r18 [1] SNPN-Identity-r18
   }
}

-- TAG-VARCONNESTFAILREPORT-STOP
-- TAG-VARCONNESTFAILREPORTLIST-START
VarConnEstFailReportList-r17 ::= SEQUENCE {
   connEstFailReportList-r17 [0] SEQUENCE (SIZE (1..maxCEFReport-r17)) OF 
      VarConnEstFailReport-r16
}

-- TAG-VARCONNESTFAILREPORTLIST-STOP
-- TAG-VARLOGMEASCONFIG-START
VarLogMeasConfig-r16 ::= SEQUENCE {
   areaConfiguration-r16 [0] AreaConfiguration-r16 OPTIONAL,
   bt-NameList-r16 [1] BT-NameList-r16 OPTIONAL,
   wlan-NameList-r16 [2] WLAN-NameList-r16 OPTIONAL,
   sensor-NameList-r16 [3] Sensor-NameList-r16 OPTIONAL,
   loggingDuration-r16 [4] LoggingDuration-r16,
   reportType [5] EXPLICIT CHOICE {
      periodical [0] LoggedPeriodicalReportConfig-r16,
      eventTriggered [1] LoggedEventTriggerConfig-r16
   },
   earlyMeasIndication-r17 [6] ENUMERATED { true(0) } OPTIONAL,
   areaConfiguration-r17 [7] AreaConfiguration-r17 OPTIONAL,
   areaConfiguration-v1800 [8] EXPLICIT AreaConfiguration-v1800 OPTIONAL
}

-- TAG-VARLOGMEASCONFIG-STOP
-- TAG-VARLOGMEASREPORT-START
VarLogMeasReport-r16 ::= SEQUENCE {
   absoluteTimeInfo-r16 [0] AbsoluteTimeInfo-r16,
   traceReference-r16 [1] TraceReference-r16,
   traceRecordingSessionRef-r16 [2] OCTET STRING (SIZE (2)),
   tce-Id-r16 [3] OCTET STRING (SIZE (1)),
   logMeasInfoList-r16 [4] LogMeasInfoList-r16,
   sigLoggedMeasType-r17 [5] ENUMERATED { true(0) },
   identityList-r18 [6] EXPLICIT CHOICE {
      plmn-IdentityList-r18 [0] PLMN-IdentityList2-r16,
      snpn-ConfigID-List-r18 [1] SNPN-ConfigID-List-r18
   }
}

-- TAG-VARLOGMEASREPORT-STOP
-- TAG-VARLTM-SERVINGCELLNORESETID-START
VarLTM-ServingCellNoResetID-r18 ::= SEQUENCE {
   ltm-ServingCellNoResetID-r18 [0] INTEGER (1..maxNrofLTM-Configs-plus1-r18) OPTIONAL
}

-- TAG-VARLTM-SERVINGCELLNORESETID-STOP
-- TAG-VARLTM-SERVINGCELLUE-MEASUREDTA-ID-START
VarLTM-ServingCellUE-MeasuredTA-ID-r18 ::= SEQUENCE {
   ltm-ServingCellUE-MeasuredTA-ID-r18 [0] INTEGER (1..maxNrofLTM-Configs-plus1-r18) OPTIONAL
}

-- TAG-VARLTM-SERVINGCELLUE-MEASUREDTA-ID-STOP
-- TAG-VARMEASCONFIG-START
VarMeasConfig ::= SEQUENCE {
     -- Measurement identities
   measIdList [0] MeasIdToAddModList OPTIONAL,
     -- Measurement objects
   measObjectList [1] MeasObjectToAddModList OPTIONAL,
     -- Reporting configurations
   reportConfigList [2] ReportConfigToAddModList OPTIONAL,
     -- Other parameters
   quantityConfig [3] QuantityConfig OPTIONAL,
   s-MeasureConfig [4] EXPLICIT CHOICE {
      ssb-RSRP [0] RSRP-Range,
      csi-RSRP [1] RSRP-Range
   } OPTIONAL
}

-- TAG-VARMEASCONFIG-STOP
-- TAG-VARMEASCONFIGSL-START
VarMeasConfigSL-r16 ::= SEQUENCE {
     -- NR sidelink measurement identities
   sl-MeasIdList-r16 [0] SL-MeasIdList-r16 OPTIONAL,
     -- NR sidelink measurement objects
   sl-MeasObjectList-r16 [1] SL-MeasObjectList-r16 OPTIONAL,
     -- NR sidelink reporting configurations
   sl-ReportConfigList-r16 [2] SL-ReportConfigList-r16 OPTIONAL,
     -- Other parameters
   sl-QuantityConfig-r16 [3] SL-QuantityConfig-r16 OPTIONAL
}

-- TAG-VARMEASCONFIGSL-STOP
-- TAG-VARMEASIDLECONFIG-START
VarMeasIdleConfig-r16 ::= SEQUENCE {
   measIdleCarrierListNR-r16 [0] SEQUENCE (SIZE (1..maxFreqIdle-r16)) OF MeasIdleCarrierNR-r16
       OPTIONAL,
   measIdleCarrierListEUTRA-r16 [1] SEQUENCE (SIZE (1..maxFreqIdle-r16)) OF 
      MeasIdleCarrierEUTRA-r16 OPTIONAL,
   measIdleDuration-r16 [2] ENUMERATED { sec10(0), sec30(1), sec60(2), 
      sec120(3), sec180(4), sec240(5), sec300(6), spare(7) },
   validityAreaList-r16 [3] ValidityAreaList-r16 OPTIONAL
}

VarEnhMeasIdleConfig-r18 ::= SEQUENCE {
   measIdleValidityDuration-r18 [0] MeasurementValidityDuration-r18 OPTIONAL
}

-- TAG-VARMEASIDLECONFIG-STOP
-- TAG-VARMEASIDLEREPORT-START
VarMeasIdleReport-r16 ::= SEQUENCE {
   measReportIdleNR-r16 [0] MeasResultIdleNR-r16 OPTIONAL,
   measReportIdleEUTRA-r16 [1] MeasResultIdleEUTRA-r16 OPTIONAL
}

CellsTriggeredList ::= SEQUENCE (SIZE (1..maxNrofCellMeas)) OF CHOICE {
   physCellId [0] PhysCellId,
   physCellIdEUTRA [1] EUTRA-PhysCellId,
   physCellIdUTRA-FDD-r16 [2] PhysCellIdUTRA-FDD-r16
}

SRS-RSRP-TriggeredList-r16 ::= SEQUENCE (SIZE (1..maxNrofCLI-SRS-Resources-r16)) OF SRS-ResourceId

CLI-RSSI-TriggeredList-r16 ::= SEQUENCE (SIZE (1..maxNrofCLI-RSSI-Resources-r16)) OF RSSI-ResourceId-r16

CLI-TriggeredList-r16 ::= CHOICE {
   srs-RSRP-TriggeredList-r16 [0] SRS-RSRP-TriggeredList-r16,
   cli-RSSI-TriggeredList-r16 [1] CLI-RSSI-TriggeredList-r16
}

RelaysTriggeredList-r17 ::= SEQUENCE (SIZE (1..maxNrofRelayMeas-r17)) OF SL-SourceIdentity-r17

VarMeasReport ::= SEQUENCE {
     -- List of measurement that have been triggered
   measId [0] MeasId,
   cellsTriggeredList [1] CellsTriggeredList OPTIONAL,
   numberOfReportsSent [2] INTEGER,
   cli-TriggeredList-r16 [3] EXPLICIT CLI-TriggeredList-r16 OPTIONAL,
   tx-PoolMeasToAddModListNR-r16 [4] Tx-PoolMeasList-r16 OPTIONAL,
   relaysTriggeredList-r17 [5] RelaysTriggeredList-r17 OPTIONAL,
   cellsMetLeavingCond-r18 [6] SEQUENCE (SIZE (1..maxCellReport)) OF PhysCellId OPTIONAL,
   reportedBestNeighbourCell-r18 [7] SEQUENCE (SIZE (1..2)) OF PhysCellId
       OPTIONAL
}

-- TAG-VARMEASIDLEREPORT-STOP
-- TAG-VARMEASREPORTLIST-START
VarMeasReportList ::= SEQUENCE (SIZE (1..maxNrofMeasId)) OF VarMeasReport

VarMeasReportSL-r16 ::= SEQUENCE {
     -- List of NR sidelink measurement that have been triggered
   sl-MeasId-r16 [0] SL-MeasId-r16,
   sl-FrequencyTriggeredList-r16 [1] SEQUENCE (SIZE (1..maxNrofFreqSL-r16)) OF ARFCN-ValueNR
       OPTIONAL,
   sl-NumberOfReportsSent-r16 [2] INTEGER
}

-- TAG-VARMEASREPORTLIST-STOP
-- TAG-VARMEASREPORTLISTSL-START
VarMeasReportListSL-r16 ::= SEQUENCE (SIZE (1..maxNrofSL-MeasId-r16)) OF VarMeasReportSL-r16

-- TAG-VARMEASREPORTLISTSL-STOP
-- TAG-VARMEASRESELECTIONCONFIG-START
VarMeasReselectionConfig-r18 ::= SEQUENCE {
   measReselectionCarrierListNR-r18 [0] SEQUENCE (SIZE (1..maxFreqIdle-r16)) OF 
      MeasReselectionCarrierNR-r18 OPTIONAL,
   measReselectionValidityDuration-r18 [1] MeasurementValidityDuration-r18
       OPTIONAL
}

VarMobilityHistoryReport-r17 ::= SEQUENCE {
   visitedCellInfoList-r16 [0] VisitedCellInfoList-r16,
   visitedPSCellInfoList-r17 [1] VisitedPSCellInfoList-r17 OPTIONAL
}

-- TAG-VARMOBILITYHISTORYREPORT-STOP
-- TAG-VARPENDINGRNA-UPDATE-START
VarPendingRNA-Update ::= SEQUENCE {
   pendingRNA-Update [0] BOOLEAN OPTIONAL
}

-- TAG-VARPENDINGRNA-UPDATE-STOP
-- TAG-VARRA-REPORT-START
VarRA-Report-r16 ::= SEQUENCE {
   ra-ReportList-r16 [0] RA-ReportList-r16,
   identityList-r18 [1] EXPLICIT CHOICE {
      plmn-IdentityList-r18 [0] PLMN-IdentityList2-r16,
      snpn-IdentityList-r18 [1] SEQUENCE (SIZE (1..maxNPN-r16)) OF SNPN-Identity-r18
   }
}

-- TAG-VARRA-REPORT-STOP
-- TAG-VARRESUMEMAC-INPUT-START
VarResumeMAC-Input ::= SEQUENCE {
   sourcePhysCellId [0] PhysCellId,
   targetCellIdentity [1] CellIdentity,
   source-c-RNTI [2] RNTI-Value
}

-- TAG-VARRESUMEMAC-INPUT-STOP
-- TAG-VARRLF-REPORT-START
VarRLF-Report-r16 ::= SEQUENCE {
   rlf-Report-r16 [0] EXPLICIT RLF-Report-r16,
   identityList-r18 [1] EXPLICIT CHOICE {
      plmn-IdentityList-r18 [0] PLMN-IdentityList2-r16,
      snpn-IdentityList-r18 [1] SEQUENCE (SIZE (1..maxNPN-r16)) OF SNPN-Identity-r18
   }
}

-- TAG-VARRLF-REPORT-STOP
-- TAG-VARSERVINGSECURITYCELLSETID-START
VarServingSecurityCellSetID ::= SEQUENCE {
   servingSecurityCellSetId-r18 [0] INTEGER (1..maxSecurityCellSet-r18)
}

-- TAG-VARSERVINGSECURITYCELLSETID-STOP
-- TAG-VARSHORTMAC-INPUT-START
VarShortMAC-Input ::= SEQUENCE {
   sourcePhysCellId [0] PhysCellId,
   targetCellIdentity [1] CellIdentity,
   source-c-RNTI [2] RNTI-Value
}

-- TAG-VARSHORTMAC-INPUT-STOP
-- TAG-VARSUCCESSHO-Report-START
VarSuccessHO-Report-r17 ::= SEQUENCE {
   successHO-Report-r17 [0] SuccessHO-Report-r17,
   identityList-r18 [1] EXPLICIT CHOICE {
      plmn-IdentityList-r18 [0] PLMN-IdentityList2-r16,
      snpn-IdentityList-r18 [1] SEQUENCE (SIZE (1..maxNPN-r16)) OF SNPN-Identity-r18
   }
}

-- TAG-VARSUCCESSHO-Report-STOP
-- TAG-VARSUCCESSPSCELL-Report-START
VarSuccessPSCell-Report-r18 ::= SEQUENCE {
   successPSCell-Report-r18 [0] SuccessPSCell-Report-r18,
   identityList-r18 [1] EXPLICIT CHOICE {
      plmn-IdentityList-r18 [0] PLMN-IdentityList2-r16,
      snpn-IdentityList-r18 [1] SEQUENCE (SIZE (1..maxNPN-r16)) OF SNPN-Identity-r18
   }
}

-- TAG-VARSUCCESSPSCELL-Report-STOP
-- TAG-VARTSS-INFO-START
VarTSS-Info-r18 ::= SEQUENCE {
   storedEventID-r18 [0] INTEGER (0..63),
   storedGlobalGnbID-r18 [1] SEQUENCE {
      plmn-Identity-r18 [0] PLMN-Identity,
      gnb-ID-r18 [1] BIT STRING  (SIZE (22..32))
   }
}

END
