NR-InterNodeDefinitions DEFINITIONS AUTOMATIC TAGS ::= BEGIN

IMPORTS

AffectedCarrierFreqCombList-r16, AffectedCarrierFreqRangeCombList-r18, 
   ARFCN-ValueNR, ARFCN-ValueEUTRA, CandidateServingFreqListNR-r16, 
   CandidateServingFreqRangeListNR-r18, CellIdentity, CGI-InfoEUTRA, CGI-InfoNR
   , CondReconfigExecCondSCG-r17, CSI-RS-Index, CSI-RS-CellMobility, DRX-Config
   , EUTRA-PhysCellId, FeatureSetDownlinkPerCC-Id, FeatureSetUplinkPerCC-Id, 
   FlightPathInfoReport-r18, FreqBandIndicatorNR, GapConfig, 
   IDC-TDM-Assistance-r18, maxBandComb, maxBands, maxBandsEUTRA, 
   maxCandidateBandIndex-r18, maxCellSFTD, maxFeatureSetsPerBand, maxFreq, 
   maxFreqIDC-MRDC, maxNrofCombIDC, maxNrofCondCells-r16, 
   maxNrofCondCells-1-r17, maxNrofPhysicalResourceBlocks, maxNrofSCells, 
   maxNrofServingCells, maxNrofServingCells-1, maxNrofServingCellsEUTRA, 
   maxNrofIndexesToReport, maxNrofLTM-Configs-r18, maxSimultaneousBands, 
   MBSInterestIndication-r17, MeasQuantityResults, MeasResultCellListSFTD-EUTRA
   , MeasResultCellListSFTD-NR, MeasResultList2NR, MeasResultSCG-Failure, 
   MeasResultServFreqListEUTRA-SCG, MUSIM-CandidateBandList-r18, 
   MUSIM-CapRestriction-r18, MUSIM-GapConfig-r17, NeedForGapsInfoNR-r16, 
   NeedForGapNCSG-InfoNR-r17, NeedForGapNCSG-InfoEUTRA-r17, 
   NeedForInterruptionInfoNR-r18, OverheatingAssistance, 
   OverheatingAssistance-r17, P-Max, PhysCellId, RadioBearerConfig, 
   RAN-NotificationAreaInfo, ReferenceConfiguration-r18, ReportConfigNR, 
   RRCReconfiguration, ServCellIndex, SetupRelease, SSB-Index, SSB-MTC, 
   SSB-ToMeasure, SS-RSSI-Measurement, ShortMAC-I, SubcarrierSpacing, 
   UEAssistanceInformation, UE-CapabilityRAT-ContainerList, 
   maxNrofCLI-RSSI-Resources-r16, maxNrofCLI-SRS-Resources-r16, 
   RSSI-ResourceId-r16, SDT-Config-r17, SidelinkUEInformationNR-r16, 
   SRS-PosRRC-InactiveValidityAreaPreConfigList-r18, SRS-ResourceId, 
   SuccessPSCell-Config-r18, SupportedAggBandwidth-r17, UE-RadioPagingInfo-r17
FROM NR-RRC-Definitions ;

-- Productions

TransmissionBandwidth-EUTRA-r16 ::= ENUMERATED { rb6(0), rb15(1), rb25(2), 
   rb50(3), rb75(4), rb100(5) }

BandCombinationIndex ::= INTEGER (1..maxBandComb)

T-Offset-r16 ::= ENUMERATED { ms0dot5(0), ms0dot75(1), ms1(2), ms1dot5(3), 
   ms2(4), ms2dot5(5), ms3(6), spare1(7) }

BandEntryIndex ::= INTEGER (0..maxNrofServingCells)

FeatureSetEntryIndex ::= INTEGER (1..maxFeatureSetsPerBand)

CG-CandidateInfoId-r17 ::= SEQUENCE {
   ssbFrequency-r17 [0] ARFCN-ValueNR,
   physCellId-r17 [1] PhysCellId
}

BandCombinationInfoSN ::= SEQUENCE {
   bandCombinationIndex [0] BandCombinationIndex,
   requestedFeatureSets [1] FeatureSetEntryIndex
}

ResourceConfigPerFR-r17 ::= SEQUENCE {
   bm-MaxNumberCSI-RS-Resource-r17 [0] INTEGER (0..64) OPTIONAL,
   bm-MaxNumberAperiodicCSI-RS-Resource-r17 [1] INTEGER (0..64) OPTIONAL,
   cg-MaxNumberConfigsAllCC-r17 [2] INTEGER (0..32) OPTIONAL,
   maxNumberCSI-RS-BFD-r17 [3] INTEGER (0..64) OPTIONAL,
   maxNumberCSI-RS-SSB-CBD-r17 [4] INTEGER (0..256) OPTIONAL,
   maxNumberSSB-BFD-r17 [5] INTEGER (0..64) OPTIONAL,
   sps-MaxNumberConfigsAllCC-r17 [6] INTEGER (0..32) OPTIONAL,
   trs-MaxConfResourceSetsAllCC-r17 [7] INTEGER (0..256) OPTIONAL,
   ...
}

-- TAG-LTM-RSOURCECONFIGNRDC-STOP
-- TAG-RESOURCECONFIGNRDC-START
ResourceConfigNRDC-r17 ::= SEQUENCE {
   fr1-ResourceConfig-r17 [0] ResourceConfigPerFR-r17 OPTIONAL,
   fr2-ResourceConfig-r17 [1] ResourceConfigPerFR-r17 OPTIONAL,
   maxNumberResAcrossCC-AcrossFR-r17 [2] INTEGER (0..256) OPTIONAL,
   ...
}

AggregatedBandwidthSN-r17 ::= SEQUENCE {
   aggBW-FDD-DL-r17 [0] EXPLICIT SupportedAggBandwidth-r17 OPTIONAL,
   aggBW-FDD-UL-r17 [1] EXPLICIT SupportedAggBandwidth-r17 OPTIONAL,
   aggBW-TDD-DL-r17 [2] EXPLICIT SupportedAggBandwidth-r17 OPTIONAL,
   aggBW-TDD-UL-r17 [3] EXPLICIT SupportedAggBandwidth-r17 OPTIONAL,
   aggBW-TotalDL-r17 [4] EXPLICIT SupportedAggBandwidth-r17 OPTIONAL,
   aggBW-TotalUL-r17 [5] EXPLICIT SupportedAggBandwidth-r17 OPTIONAL
}

-- TAG-UE-RADIO-ACCESS-CAPABILITY-INFORMATION-STOP
-- TAG-L1-MEASCONFIGNRDC-START
L1-MeasConfigNRDC-r18 ::= SEQUENCE {
   maxL1-MeasNoGapSCG-r18 [0] INTEGER (0..maxNrofL1-MeasNoGap-r18) OPTIONAL,
   maxL1-MeasWithGapSCG-r18 [1] INTEGER (0..maxNrofL1-MeasWithGap-r18) OPTIONAL,
   maxCellsL1-MeasNoGapSCG-r18 [2] INTEGER (0..maxNrofCellsL1-MeasNoGap-r18) OPTIONAL,
   maxCellsL1-MeasWithGapSCG-r18 [3] INTEGER (0..maxNrofCellsL1-MeasWithGap-r18) OPTIONAL,
   maxTotalCellsL1-MeasNoGapSCG-r18 [4] INTEGER (0..maxNrofTotalCellsL1-MeasNoGap-r18) OPTIONAL,
   maxSSBsL1-MeasNoGapSCG-r18 [5] INTEGER (0..maxNrofSSBsL1-MeasNoGap-r18) OPTIONAL,
   maxSSBsL1-MeasWithGapSCG-r18 [6] INTEGER (0..maxNrofSSBsL1-MeasWithGap-r18) OPTIONAL,
   maxTotalSSBsL1-MeasNoGapSCG-r18 [7] INTEGER (0..maxNrofTotalSSBsL1-MeasNoGap-r18) OPTIONAL,
   maxCellsL1-MeasIntraFreqSCG-r18 [8] INTEGER (0..maxNrofSSBsL1-MeasIntraFreq-r18) OPTIONAL,
   maxCellsL1-MeasInterFreqSCG-r18 [9] INTEGER (0..maxNrofSSBsL1-MeasInterFreq-r18) OPTIONAL,
   maxReportConfigsAperiodic-r18 [10] INTEGER (0..maxNrofReportConfigsAperiodic-r18) OPTIONAL,
   maxReportConfigsPeriodic-r18 [11] INTEGER (0..maxNrofReportConfigsPeriodic-r18) OPTIONAL,
   maxReportConfigsSemiPersistent-r18 [12] INTEGER (0..maxNrofReportConfigsSemiPersistent-r18) OPTIONAL,
   ...,
   [[
      maxSSBsL1-MeasNoGapSCGExt-r18 [13] INTEGER (0..maxNrofSSBsL1-MeasNoGapExt-r18) OPTIONAL
   ]]
}

-- TAG-L1-MEASCONFIGNRDC-STOP
-- TAG-LTM-RESOURCECONFIGNRDC-START
LTM-ResourceConfigNRDC-r18 ::= SEQUENCE {
   maxCellsTA-Meas-r18 [0] INTEGER (0..maxNrofCellsTA-Meas-r18) OPTIONAL,
   maxConfigJointTCI-States-r18 [1] INTEGER (0..maxNrofConfigJointTCI-States-r18) OPTIONAL,
   maxCellsJointTCI-r18 [2] INTEGER (0..maxNrofCellsTCI-r18) OPTIONAL,
   maxConfigDL-TCI-States-r18 [3] INTEGER (0..maxNrofConfigDL-TCI-States-r18) OPTIONAL,
   maxConfigUL-TCI-States-r18 [4] INTEGER (0..maxNrofConfigUL-TCI-States-r18) OPTIONAL,
   maxCellsTCI-r18 [5] INTEGER (0..maxNrofCellsTCI-r18) OPTIONAL,
   maxStoredConfigCells-r18 [6] INTEGER (0..maxNrofStoredConfigCells-r18) OPTIONAL,
   maxConfigCells-r18 [7] INTEGER (0..maxNrofConfigCells-r18) OPTIONAL,
   maxActivatedJointTCI-States-r18 [8] INTEGER (0..maxNrofActivatedJointTCI-States-r18) OPTIONAL,
   maxActivatedDL-TCI-States-r18 [9] INTEGER (0..maxNrofActivatedDL-TCI-States-r18) OPTIONAL,
   maxActivatedUL-TCI-States-r18 [10] INTEGER (0..maxNrofActivatedUL-TCI-States-r18) OPTIONAL,
   ...
}

ConfigRestrictModReqSCG ::= SEQUENCE {
   requestedBC-MRDC [0] BandCombinationInfoSN OPTIONAL,
   requestedP-MaxFR1 [1] P-Max OPTIONAL,
   ...,
   [[
      requestedPDCCH-BlindDetectionSCG [2] INTEGER (1..15) OPTIONAL,
      requestedP-MaxEUTRA [3] P-Max OPTIONAL
   ]],
   [[
      requestedP-MaxFR2-r16 [4] P-Max OPTIONAL,
      requestedMaxInterFreqMeasIdSCG-r16 [5] INTEGER (1..maxMeasIdentitiesMN) OPTIONAL,
      requestedMaxIntraFreqMeasIdSCG-r16 [6] INTEGER (1..maxMeasIdentitiesMN) OPTIONAL,
      requestedToffset-r16 [7] T-Offset-r16 OPTIONAL
   ]],
   [[
      reservedResourceConfigNRDC-r17 [8] ResourceConfigNRDC-r17 OPTIONAL
   ]],
   [[
      aggregatedBandwidthSN-r17 [9] AggregatedBandwidthSN-r17 OPTIONAL
   ]],
   [[
      requestedMaxLTM-CandidateIdSCG-r18 [10] INTEGER (0..maxNrofLTM-Configs-r18) OPTIONAL
   ]],
   [[
      requestedL1-MeasConfigNRDC-r18 [11] L1-MeasConfigNRDC-r18 OPTIONAL
   ]],
   [[
      requestedLTM-ResourceConfigNRDC-r18 [12] LTM-ResourceConfigNRDC-r18
          OPTIONAL
   ]]
}

DRX-Info ::= SEQUENCE {
   drx-LongCycleStartOffset [0] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   shortDRX [1] SEQUENCE {
      drx-ShortCycle [0] ENUMERATED { ms2(0), ms3(1), ms4(2), ms5(3), ms6(4), 
         ms7(5), ms8(6), ms10(7), ms14(8), ms16(9), ms20(10), ms30(11), 
         ms32(12), ms35(13), ms40(14), ms64(15), ms80(16), ms128(17), ms160(18)
         , ms256(19), ms320(20), ms512(21), ms640(22), spare9(23), spare8(24), 
         spare7(25), spare6(26), spare5(27), spare4(28), spare3(29), spare2(30)
         , spare1(31) },
      drx-ShortCycleTimer [1] INTEGER (1..16)
   } OPTIONAL
}

NR-FreqInfo ::= SEQUENCE {
   measuredFrequency [0] ARFCN-ValueNR OPTIONAL,
   ...
}

MeasConfigSN ::= SEQUENCE {
   measuredFrequenciesSN [0] SEQUENCE (SIZE (1..maxMeasFreqsSN)) OF NR-FreqInfo OPTIONAL,
   ...
}

FR-Info ::= SEQUENCE {
   servCellIndex [0] ServCellIndex,
   fr-Type [1] ENUMERATED { fr1(0), fr2(1) }
}

FR-InfoList ::= SEQUENCE (SIZE (1..maxNrofServingCells-1)) OF FR-Info

CandidateServingFreqListNR ::= SEQUENCE (SIZE (1..maxFreqIDC-MRDC)) OF ARFCN-ValueNR

PH-UplinkCarrierSCG ::= SEQUENCE {
   ph-Type1or3 [0] ENUMERATED { type1(0), type3(1) },
   ...
}

PH-InfoSCG ::= SEQUENCE {
   servCellIndex [0] ServCellIndex,
   ph-Uplink [1] PH-UplinkCarrierSCG,
   ph-SupplementaryUplink [2] PH-UplinkCarrierSCG OPTIONAL,
   ...,
   [[
      twoSRS-PUSCH-Repetition-r17 [3] ENUMERATED { enabled(0) } OPTIONAL
   ]],
   [[
      twoSRS-MultipanelScheme-r18 [4] ENUMERATED { enabled(0) } OPTIONAL
   ]]
}

PH-TypeListSCG ::= SEQUENCE (SIZE (1..maxNrofServingCells)) OF PH-InfoSCG

CandidateServingFreqListEUTRA ::= SEQUENCE (SIZE (1..maxFreqIDC-MRDC)) OF ARFCN-ValueEUTRA

DRX-Info2 ::= SEQUENCE {
   drx-onDurationTimer [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   }
}

FrequencyConfig-NR-r16 ::= SEQUENCE {
   freqBandIndicatorNR-r16 [0] FreqBandIndicatorNR,
   carrierCenterFreq-NR-r16 [1] ARFCN-ValueNR,
   carrierBandwidth-NR-r16 [2] INTEGER (1..maxNrofPhysicalResourceBlocks),
   subcarrierSpacing-NR-r16 [3] SubcarrierSpacing
}

ServCellInfoXCG-NR-r16 ::= SEQUENCE {
   dl-FreqInfo-NR-r16 [0] FrequencyConfig-NR-r16 OPTIONAL,
   ul-FreqInfo-NR-r16 [1] FrequencyConfig-NR-r16 OPTIONAL,
   ...
}

ServCellInfoListSCG-NR-r16 ::= SEQUENCE (SIZE (1..maxNrofServingCells)) OF ServCellInfoXCG-NR-r16

ServCellInfoXCG-EUTRA-r16 ::= SEQUENCE {
   dl-CarrierFreq-EUTRA-r16 [0] ARFCN-ValueEUTRA OPTIONAL,
   ul-CarrierFreq-EUTRA-r16 [1] ARFCN-ValueEUTRA OPTIONAL, -- Cond FDD
   transmissionBandwidth-EUTRA-r16 [2] TransmissionBandwidth-EUTRA-r16 OPTIONAL
      ,
   ...
}

ServCellInfoListSCG-EUTRA-r16 ::= SEQUENCE (SIZE (1..maxNrofServingCellsEUTRA)) OF 
   ServCellInfoXCG-EUTRA-r16

CandidateCell-r17 ::= SEQUENCE {
   physCellId-r17 [0] PhysCellId,
   condExecutionCondSCG-r17 [1] OCTET STRING (CONTAINING 
      CondReconfigExecCondSCG-r17) OPTIONAL
}

CandidateCellInfo-r17 ::= SEQUENCE {
   ssbFrequency-r17 [0] ARFCN-ValueNR,
   candidateList-r17 [1] SEQUENCE (SIZE (1..maxNrofCondCells-r16)) OF CandidateCell-r17
}

CandidateCellInfoListCPC-r17 ::= SEQUENCE (SIZE (1..maxFreq)) OF CandidateCellInfo-r17

CG-Config-v1800-IEs ::= SEQUENCE {
   candidateServingFreqRangeListNR-r18 [0] CandidateServingFreqRangeListNR-r18
       OPTIONAL,
   candidateServingFreqListNR-r18 [1] CandidateServingFreqListNR-r16 OPTIONAL,
   idc-TDM-AssistanceConfig-r18 [2] ENUMERATED { enabled(0) } OPTIONAL,
   candidateCellInfoListSubsequentCPC-r18 [3] CandidateCellInfoListCPC-r17
       OPTIONAL,
   scpac-ReferenceConfigurationSCG-r18 [4] ReferenceConfiguration-r18 OPTIONAL,
   subsequentCPAC-Information-r18 [5] CandidateCellInfoListCPC-r17 OPTIONAL,
   successPSCell-Config-r18 [6] SuccessPSCell-Config-r18 OPTIONAL,
   nonCriticalExtension [7] SEQUENCE {

   } OPTIONAL
}

CG-Config-v1730-IEs ::= SEQUENCE {
   fr1-Carriers-SCG-r17 [0] INTEGER (1..32) OPTIONAL,
   fr2-Carriers-SCG-r17 [1] INTEGER (1..32) OPTIONAL,
   nonCriticalExtension [2] CG-Config-v1800-IEs OPTIONAL
}

CG-Config-v1700-IEs ::= SEQUENCE {
   candidateCellInfoListCPC-r17 [0] CandidateCellInfoListCPC-r17 OPTIONAL,
   twoPHRModeSCG-r17 [1] ENUMERATED { enabled(0) } OPTIONAL,
   nonCriticalExtension [2] CG-Config-v1730-IEs OPTIONAL
}

CG-Config-v1640-IEs ::= SEQUENCE {
   servCellInfoListSCG-NR-r16 [0] ServCellInfoListSCG-NR-r16 OPTIONAL,
   servCellInfoListSCG-EUTRA-r16 [1] ServCellInfoListSCG-EUTRA-r16 OPTIONAL,
   nonCriticalExtension [2] CG-Config-v1700-IEs OPTIONAL
}

CG-Config-v1630-IEs ::= SEQUENCE {
   selectedToffset-r16 [0] T-Offset-r16 OPTIONAL,
   nonCriticalExtension [1] CG-Config-v1640-IEs OPTIONAL
}

CG-Config-v1620-IEs ::= SEQUENCE {
   ueAssistanceInformationSCG-r16 [0] OCTET STRING (CONTAINING 
      UEAssistanceInformation) OPTIONAL,
   nonCriticalExtension [1] CG-Config-v1630-IEs OPTIONAL
}

CG-Config-v1610-IEs ::= SEQUENCE {
   drx-InfoSCG2 [0] DRX-Info2 OPTIONAL,
   nonCriticalExtension [1] CG-Config-v1620-IEs OPTIONAL
}

CG-Config-v1590-IEs ::= SEQUENCE {
   scellFrequenciesSN-NR [0] SEQUENCE (SIZE (1..maxNrofServingCells-1)) OF ARFCN-ValueNR OPTIONAL,
   scellFrequenciesSN-EUTRA [1] SEQUENCE (SIZE (1..maxNrofServingCells-1)) OF ARFCN-ValueEUTRA
       OPTIONAL,
   nonCriticalExtension [2] CG-Config-v1610-IEs OPTIONAL
}

CG-Config-v1560-IEs ::= SEQUENCE {
   pSCellFrequencyEUTRA [0] ARFCN-ValueEUTRA OPTIONAL,
   scg-CellGroupConfigEUTRA [1] OCTET STRING OPTIONAL,
   candidateCellInfoListSN-EUTRA [2] OCTET STRING OPTIONAL,
   candidateServingFreqListEUTRA [3] CandidateServingFreqListEUTRA OPTIONAL,
   needForGaps [4] ENUMERATED { true(0) } OPTIONAL,
   drx-ConfigSCG [5] DRX-Config OPTIONAL,
   reportCGI-RequestEUTRA [6] SEQUENCE {
      requestedCellInfoEUTRA [0] SEQUENCE {
         eutraFrequency [0] ARFCN-ValueEUTRA,
         cellForWhichToReportCGI-EUTRA [1] EUTRA-PhysCellId
      } OPTIONAL
   } OPTIONAL,
   nonCriticalExtension [7] CG-Config-v1590-IEs OPTIONAL
}

CG-Config-v1540-IEs ::= SEQUENCE {
   pSCellFrequency [0] ARFCN-ValueNR OPTIONAL,
   reportCGI-RequestNR [1] SEQUENCE {
      requestedCellInfo [0] SEQUENCE {
         ssbFrequency [0] ARFCN-ValueNR,
         cellForWhichToReportCGI [1] PhysCellId
      } OPTIONAL
   } OPTIONAL,
   ph-InfoSCG [2] PH-TypeListSCG OPTIONAL,
   nonCriticalExtension [3] CG-Config-v1560-IEs OPTIONAL
}

CG-Config-IEs ::= SEQUENCE {
   scg-CellGroupConfig [0] OCTET STRING (CONTAINING RRCReconfiguration)
       OPTIONAL,
   scg-RB-Config [1] OCTET STRING (CONTAINING RadioBearerConfig) OPTIONAL,
   configRestrictModReq [2] ConfigRestrictModReqSCG OPTIONAL,
   drx-InfoSCG [3] DRX-Info OPTIONAL,
   candidateCellInfoListSN [4] OCTET STRING (CONTAINING MeasResultList2NR)
       OPTIONAL,
   measConfigSN [5] MeasConfigSN OPTIONAL,
   selectedBandCombination [6] BandCombinationInfoSN OPTIONAL,
   fr-InfoListSCG [7] FR-InfoList OPTIONAL,
   candidateServingFreqListNR [8] CandidateServingFreqListNR OPTIONAL,
   nonCriticalExtension [9] CG-Config-v1540-IEs OPTIONAL
}

-- TAG-HANDOVER-PREPARATION-INFORMATION-STOP
-- TAG-CG-CONFIG-START
CG-Config ::= SEQUENCE {
   criticalExtensions [0] EXPLICIT CHOICE {
      c1 [0] EXPLICIT CHOICE {
         cg-Config [0] CG-Config-IEs,
         spare3 [1] NULL,
         spare2 [2] NULL,
         spare1 [3] NULL
      },
      criticalExtensionsFuture [1] SEQUENCE {

      }
   }
}

CG-CandidateInfo-r17 ::= SEQUENCE {
   cg-CandidateInfoId-r17 [0] CG-CandidateInfoId-r17,
   candidateCG-Config-r17 [1] OCTET STRING (CONTAINING CG-Config)
}

CG-CandidateList-r17-IEs ::= SEQUENCE {
   cg-CandidateToAddModList-r17 [0] SEQUENCE (SIZE (1..maxNrofCondCells-r16)) OF 
      CG-CandidateInfo-r17 OPTIONAL,
   cg-CandidateToReleaseList-r17 [1] SEQUENCE (SIZE (1..maxNrofCondCells-r16)) OF 
      CG-CandidateInfoId-r17 OPTIONAL,
   nonCriticalExtension [2] SEQUENCE {

   } OPTIONAL
}

-- TAG-NR-INTER-NODE-DEFINITIONS-STOP
-- TAG-CG-CANDIDATELIST-START
CG-CandidateList ::= SEQUENCE {
   criticalExtensions [0] EXPLICIT CHOICE {
      c1 [0] EXPLICIT CHOICE {
         cg-CandidateList-r17 [0] CG-CandidateList-r17-IEs,
         spare3 [1] NULL,
         spare2 [2] NULL,
         spare1 [3] NULL
      },
      criticalExtensionsFuture [1] SEQUENCE {

      }
   }
}

CandPSCellExecutionConditionInfo-r18 ::= SEQUENCE {
   candPSCellExecCondReportConfigNR-r18 [0] SEQUENCE (SIZE (1..2)) OF 
      ReportConfigNR,
   ...
}

HandoverCommand-v1800-IEs ::= SEQUENCE {
   candPSCellExecutionConditionInfo-r18 [0] 
      CandPSCellExecutionConditionInfo-r18 OPTIONAL,
   nonCriticalExtension [1] SEQUENCE {

   } OPTIONAL
}

HandoverCommand-IEs ::= SEQUENCE {
   handoverCommandMessage [0] OCTET STRING (CONTAINING RRCReconfiguration),
   nonCriticalExtension [1] HandoverCommand-v1800-IEs OPTIONAL
}

-- TAG-CG-CANDIDATELIST-STOP
-- TAG-HANDOVER-COMMAND-START
HandoverCommand ::= SEQUENCE {
   criticalExtensions [0] EXPLICIT CHOICE {
      c1 [0] EXPLICIT CHOICE {
         handoverCommand [0] HandoverCommand-IEs,
         spare3 [1] NULL,
         spare2 [2] NULL,
         spare1 [3] NULL
      },
      criticalExtensionsFuture [1] SEQUENCE {

      }
   }
}

AS-Config ::= SEQUENCE {
   rrcReconfiguration [0] OCTET STRING (CONTAINING RRCReconfiguration),
   ...,
   [[
      sourceRB-SN-Config [1] OCTET STRING (CONTAINING RadioBearerConfig)
          OPTIONAL,
      sourceSCG-NR-Config [2] OCTET STRING (CONTAINING RRCReconfiguration)
          OPTIONAL,
      sourceSCG-EUTRA-Config [3] OCTET STRING OPTIONAL
   ]],
   [[
      sourceSCG-Configured [4] ENUMERATED { true(0) } OPTIONAL
   ]],
   [[
      sdt-Config-r17 [5] SDT-Config-r17 OPTIONAL
   ]],
   [[
      srs-PosRRC-InactiveValidityAreaPreConfigList-r18 [6] 
         SRS-PosRRC-InactiveValidityAreaPreConfigList-r18 OPTIONAL
   ]]
}

RRM-Config ::= SEQUENCE {
   ue-InactiveTime [0] ENUMERATED { s1(0), s2(1), s3(2), s5(3), s7(4), s10(5), 
      s15(6), s20(7), s25(8), s30(9), s40(10), s50(11), min1(12), min1s20(13), 
      min1s40(14), min2(15), min2s30(16), min3(17), min3s30(18), min4(19), 
      min5(20), min6(21), min7(22), min8(23), min9(24), min10(25), min12(26), 
      min14(27), min17(28), min20(29), min24(30), min28(31), min33(32), 
      min38(33), min44(34), min50(35), hr1(36), hr1min30(37), hr2(38), 
      hr2min30(39), hr3(40), hr3min30(41), hr4(42), hr5(43), hr6(44), hr8(45), 
      hr10(46), hr13(47), hr16(48), hr20(49), day1(50), day1hr12(51), day2(52)
      , day2hr12(53), day3(54), day4(55), day5(56), day7(57), day10(58), 
      day14(59), day19(60), day24(61), day30(62), dayMoreThan30(63) } OPTIONAL,
   candidateCellInfoList [1] MeasResultList2NR OPTIONAL,
   ...,
   [[
      candidateCellInfoListSN-EUTRA [2] MeasResultServFreqListEUTRA-SCG
          OPTIONAL
   ]]
}

ReestabNCellInfo ::= SEQUENCE {
   cellIdentity [0] CellIdentity,
   key-gNodeB-Star [1] BIT STRING  (SIZE (256)),
   shortMAC-I [2] ShortMAC-I
}

ReestabNCellInfoList ::= SEQUENCE (SIZE (1..maxCellPrep)) OF ReestabNCellInfo

ReestablishmentInfo ::= SEQUENCE {
   sourcePhysCellId [0] PhysCellId,
   targetCellShortMAC-I [1] ShortMAC-I,
   additionalReestabInfoList [2] ReestabNCellInfoList OPTIONAL
}

BandCombinationInfo ::= SEQUENCE {
   bandCombinationIndex [0] BandCombinationIndex,
   allowedFeatureSetsList [1] SEQUENCE (SIZE (1..maxFeatureSetsPerBand)) OF FeatureSetEntryIndex
}

BandCombinationInfoList ::= SEQUENCE (SIZE (1..maxBandComb)) OF BandCombinationInfo

SelectedBandEntriesMN ::= SEQUENCE (SIZE (1..maxSimultaneousBands)) OF BandEntryIndex

AllowedAggregatedBandwidth-r17 ::= SEQUENCE {
   bandCombinationIndex-r17 [0] BandCombinationIndex,
   allowedAggBW-FDD-DL-r17 [1] EXPLICIT SupportedAggBandwidth-r17 OPTIONAL,
   allowedAggBW-FDD-UL-r17 [2] EXPLICIT SupportedAggBandwidth-r17 OPTIONAL,
   allowedAggBW-TDD-DL-r17 [3] EXPLICIT SupportedAggBandwidth-r17 OPTIONAL,
   allowedAggBW-TDD-UL-r17 [4] EXPLICIT SupportedAggBandwidth-r17 OPTIONAL,
   allowedAggBW-TotalDL-r17 [5] EXPLICIT SupportedAggBandwidth-r17 OPTIONAL,
   allowedAggBW-TotalUL-r17 [6] EXPLICIT SupportedAggBandwidth-r17 OPTIONAL
}

AllowedAggregatedBandwidthSNList-r17 ::= SEQUENCE (SIZE (1..maxBandComb)) OF 
   AllowedAggregatedBandwidth-r17

ConfigRestrictInfoSCG ::= SEQUENCE {
   allowedBC-ListMRDC [0] BandCombinationInfoList OPTIONAL,
   powerCoordination-FR1 [1] SEQUENCE {
      p-maxNR-FR1 [0] P-Max OPTIONAL,
      p-maxEUTRA [1] P-Max OPTIONAL,
      p-maxUE-FR1 [2] P-Max OPTIONAL
   } OPTIONAL,
   servCellIndexRangeSCG [2] SEQUENCE {
      lowBound [0] ServCellIndex,
      upBound [1] ServCellIndex
   } OPTIONAL, -- Cond SN-AddMod
   maxMeasFreqsSCG [3] INTEGER (1..maxMeasFreqsMN) OPTIONAL,
   dummy [4] INTEGER (1..maxMeasIdentitiesMN) OPTIONAL,
   ...,
   [[
      selectedBandEntriesMNList [5] SEQUENCE (SIZE (1..maxBandComb)) OF 
         SelectedBandEntriesMN OPTIONAL,
      pdcch-BlindDetectionSCG [6] INTEGER (1..15) OPTIONAL,
      maxNumberROHC-ContextSessionsSN [7] INTEGER (0..16384) OPTIONAL
   ]],
   [[
      maxIntraFreqMeasIdentitiesSCG [8] INTEGER (1..maxMeasIdentitiesMN) OPTIONAL,
      maxInterFreqMeasIdentitiesSCG [9] INTEGER (1..maxMeasIdentitiesMN) OPTIONAL
   ]],
   [[
      p-maxNR-FR1-MCG-r16 [10] P-Max OPTIONAL,
      powerCoordination-FR2-r16 [11] SEQUENCE {
         p-maxNR-FR2-MCG-r16 [0] P-Max OPTIONAL,
         p-maxNR-FR2-SCG-r16 [1] P-Max OPTIONAL,
         p-maxUE-FR2-r16 [2] P-Max OPTIONAL
      } OPTIONAL,
      nrdc-PC-mode-FR1-r16 [12] ENUMERATED { semi-static-mode1(0), 
         semi-static-mode2(1), dynamic(2) } OPTIONAL,
      nrdc-PC-mode-FR2-r16 [13] ENUMERATED { semi-static-mode1(0), 
         semi-static-mode2(1), dynamic(2) } OPTIONAL,
      maxMeasSRS-ResourceSCG-r16 [14] INTEGER (0..maxNrofCLI-SRS-Resources-r16) OPTIONAL,
      maxMeasCLI-ResourceSCG-r16 [15] INTEGER (0..maxNrofCLI-RSSI-Resources-r16) OPTIONAL,
      maxNumberEHC-ContextsSN-r16 [16] INTEGER (0..65536) OPTIONAL,
      allowedReducedConfigForOverheating-r16 [17] OverheatingAssistance
          OPTIONAL,
      maxToffset-r16 [18] T-Offset-r16 OPTIONAL
   ]],
   [[
      allowedReducedConfigForOverheating-r17 [19] OverheatingAssistance-r17
          OPTIONAL,
      maxNumberUDC-DRB-r17 [20] INTEGER (0..2) OPTIONAL,
      maxNumberCPCCandidates-r17 [21] INTEGER (0..maxNrofCondCells-1-r17) OPTIONAL
   ]],
   [[
      allowedResourceConfigNRDC-r17 [22] ResourceConfigNRDC-r17 OPTIONAL
   ]],
   [[
      allowedAggregatedBandwidthSNList-r17 [23] 
         AllowedAggregatedBandwidthSNList-r17 OPTIONAL
   ]],
   [[
      maxNumberLTM-CandidatesSCG-r18 [24] INTEGER (0..maxNrofLTM-Configs-r18) OPTIONAL
   ]],
   [[
      allowedL1-MeasConfigNRDC-r18 [25] L1-MeasConfigNRDC-r18 OPTIONAL
   ]],
   [[
      allowedLTM-ResourceConfigNRDC-r18 [26] LTM-ResourceConfigNRDC-r18
          OPTIONAL
   ]]
}

ConfigRestrictInfoDAPS-r16 ::= SEQUENCE {
   powerCoordination-r16 [0] SEQUENCE {
      p-DAPS-Source-r16 [0] P-Max,
      p-DAPS-Target-r16 [1] P-Max,
      uplinkPowerSharingDAPS-Mode-r16 [2] ENUMERATED { semi-static-mode1(0), 
         semi-static-mode2(1), dynamic(2) }
   } OPTIONAL
}

ConfigRestrictInfoDAPS-v1640 ::= SEQUENCE {
   sourceFeatureSetPerDownlinkCC-r16 [0] FeatureSetDownlinkPerCC-Id,
   sourceFeatureSetPerUplinkCC-r16 [1] FeatureSetUplinkPerCC-Id
}

AS-Context ::= SEQUENCE {
   reestablishmentInfo [0] ReestablishmentInfo OPTIONAL,
   configRestrictInfo [1] ConfigRestrictInfoSCG OPTIONAL,
   ...,
   [[
      ran-NotificationAreaInfo [2] EXPLICIT RAN-NotificationAreaInfo OPTIONAL
   ]],
   [[
      ueAssistanceInformation [3] OCTET STRING (CONTAINING 
         UEAssistanceInformation) OPTIONAL
   ]],
   [[
      selectedBandCombinationSN [4] BandCombinationInfoSN OPTIONAL
   ]],
   [[
      configRestrictInfoDAPS-r16 [5] ConfigRestrictInfoDAPS-r16 OPTIONAL,
      sidelinkUEInformationNR-r16 [6] OCTET STRING OPTIONAL,
      sidelinkUEInformationEUTRA-r16 [7] OCTET STRING OPTIONAL,
      ueAssistanceInformationEUTRA-r16 [8] OCTET STRING OPTIONAL,
      ueAssistanceInformationSCG-r16 [9] OCTET STRING (CONTAINING 
         UEAssistanceInformation) OPTIONAL,
      needForGapsInfoNR-r16 [10] NeedForGapsInfoNR-r16 OPTIONAL
   ]],
   [[
      configRestrictInfoDAPS-v1640 [11] ConfigRestrictInfoDAPS-v1640 OPTIONAL
   ]],
   [[
      needForGapNCSG-InfoNR-r17 [12] NeedForGapNCSG-InfoNR-r17 OPTIONAL,
      needForGapNCSG-InfoEUTRA-r17 [13] NeedForGapNCSG-InfoEUTRA-r17 OPTIONAL,
      mbsInterestIndication-r17 [14] OCTET STRING (CONTAINING 
         MBSInterestIndication-r17) OPTIONAL
   ]],
   [[
      needForInterruptionInfoNR-r18 [15] NeedForInterruptionInfoNR-r18 OPTIONAL
         ,
      flightPathInfoReport-r18 [16] FlightPathInfoReport-r18 OPTIONAL
   ]]
}

HandoverPreparationInformation-IEs ::= SEQUENCE {
   ue-CapabilityRAT-List [0] UE-CapabilityRAT-ContainerList,
   sourceConfig [1] AS-Config OPTIONAL, -- Cond HO
   rrm-Config [2] RRM-Config OPTIONAL,
   as-Context [3] AS-Context OPTIONAL,
   nonCriticalExtension [4] SEQUENCE {

   } OPTIONAL
}

-- TAG-HANDOVER-COMMAND-STOP
-- TAG-HANDOVER-PREPARATION-INFORMATION-START
HandoverPreparationInformation ::= SEQUENCE {
   criticalExtensions [0] EXPLICIT CHOICE {
      c1 [0] EXPLICIT CHOICE {
         handoverPreparationInformation [0] HandoverPreparationInformation-IEs,
         spare3 [1] NULL,
         spare2 [2] NULL,
         spare1 [3] NULL
      },
      criticalExtensionsFuture [1] SEQUENCE {

      }
   }
}

MeasConfigMN ::= SEQUENCE {
   measuredFrequenciesMN [0] SEQUENCE (SIZE (1..maxMeasFreqsMN)) OF NR-FreqInfo OPTIONAL,
   measGapConfig [1] EXPLICIT CHOICE {
      release [0] NULL,
      setup [1] EXPLICIT GapConfig
   } OPTIONAL,
   gapPurpose [2] ENUMERATED { perUE(0), perFR1(1) } OPTIONAL,
   ...,
   [[
      measGapConfigFR2 [3] EXPLICIT CHOICE {
         release [0] NULL,
         setup [1] EXPLICIT GapConfig
      } OPTIONAL
   ]],
   [[
      interFreqNoGap-r16 [4] ENUMERATED { true(0) } OPTIONAL
   ]]
}

VictimSystemType ::= SEQUENCE {
   gps [0] ENUMERATED { true(0) } OPTIONAL,
   glonass [1] ENUMERATED { true(0) } OPTIONAL,
   bds [2] ENUMERATED { true(0) } OPTIONAL,
   galileo [3] ENUMERATED { true(0) } OPTIONAL,
   wlan [4] ENUMERATED { true(0) } OPTIONAL,
   bluetooth [5] ENUMERATED { true(0) } OPTIONAL
}

AffectedCarrierFreqCombEUTRA ::= SEQUENCE (SIZE (1..maxNrofServingCellsEUTRA)) OF ARFCN-ValueEUTRA

AffectedCarrierFreqCombNR ::= SEQUENCE (SIZE (1..maxNrofServingCells)) OF ARFCN-ValueNR

AffectedCarrierFreqCombInfoMRDC ::= SEQUENCE {
   victimSystemType [0] VictimSystemType,
   interferenceDirectionMRDC [1] ENUMERATED { eutra-nr(0), nr(1), other(2), 
      utra-nr-other(3), nr-other(4), spare3(5), spare2(6), spare1(7) },
   affectedCarrierFreqCombMRDC [2] SEQUENCE {
      affectedCarrierFreqCombEUTRA [0] AffectedCarrierFreqCombEUTRA OPTIONAL,
      affectedCarrierFreqCombNR [1] AffectedCarrierFreqCombNR
   } OPTIONAL
}

MRDC-AssistanceInfo ::= SEQUENCE {
   affectedCarrierFreqCombInfoListMRDC [0] SEQUENCE (SIZE (1..maxNrofCombIDC)) OF 
      AffectedCarrierFreqCombInfoMRDC,
   ...,
   [[
      overheatingAssistanceSCG-r16 [1] OCTET STRING (CONTAINING 
         OverheatingAssistance) OPTIONAL
   ]],
   [[
      overheatingAssistanceSCG-FR2-2-r17 [2] OCTET STRING (CONTAINING 
         OverheatingAssistance-r17) OPTIONAL
   ]],
   [[
      affectedCarrierFreqRangeCombList-r18 [3] 
         AffectedCarrierFreqRangeCombList-r18 OPTIONAL,
      affectedCarrierFreqCombList-r18 [4] AffectedCarrierFreqCombList-r16
          OPTIONAL,
      idc-TDM-Assistance-r18 [5] IDC-TDM-Assistance-r18 OPTIONAL
   ]]
}

PH-UplinkCarrierMCG ::= SEQUENCE {
   ph-Type1or3 [0] ENUMERATED { type1(0), type3(1) },
   ...
}

PH-InfoMCG ::= SEQUENCE {
   servCellIndex [0] ServCellIndex,
   ph-Uplink [1] PH-UplinkCarrierMCG,
   ph-SupplementaryUplink [2] PH-UplinkCarrierMCG OPTIONAL,
   ...,
   [[
      twoSRS-PUSCH-Repetition-r17 [3] ENUMERATED { enabled(0) } OPTIONAL
   ]],
   [[
      twoSRS-MultipanelScheme-r18 [4] ENUMERATED { enabled(0) } OPTIONAL
   ]]
}

PH-TypeListMCG ::= SEQUENCE (SIZE (1..maxNrofServingCells)) OF PH-InfoMCG

SFTD-FrequencyList-NR ::= SEQUENCE (SIZE (1..maxCellSFTD)) OF ARFCN-ValueNR

SFTD-FrequencyList-EUTRA ::= SEQUENCE (SIZE (1..maxCellSFTD)) OF ARFCN-ValueEUTRA

ServCellInfoListMCG-NR-r16 ::= SEQUENCE (SIZE (1..maxNrofServingCells)) OF ServCellInfoXCG-NR-r16

ServCellInfoListMCG-EUTRA-r16 ::= SEQUENCE (SIZE (1..maxNrofServingCellsEUTRA)) OF 
   ServCellInfoXCG-EUTRA-r16

CandidateCellCPC-r17 ::= SEQUENCE {
   ssbFrequency-r17 [0] ARFCN-ValueNR,
   candidateCellList-r17 [1] SEQUENCE (SIZE (1..maxNrofCondCells-r16)) OF PhysCellId
}

CandidateCellListCPC-r17 ::= SEQUENCE (SIZE (1..maxFreq)) OF CandidateCellCPC-r17

CG-ConfigInfo-v1800-IEs ::= SEQUENCE {
   musim-GapConfigInfo-r18 [0] MUSIM-GapConfig-r17 OPTIONAL,
   musim-CapRestrictionInfo-r18 [1] SEQUENCE {
      musim-CapRestriction-r18 [0] MUSIM-CapRestriction-r18 OPTIONAL,
      musim-CandidateBandList-r18 [1] MUSIM-CandidateBandList-r18 OPTIONAL
   } OPTIONAL,
   scpac-ReferenceConfiguration-r18 [2] ReferenceConfiguration-r18 OPTIONAL,
   subsequentCPAC-Candidates-r18 [3] CandidateCellListCPC-r17 OPTIONAL,
   nonCriticalExtension [4] SEQUENCE {

   } OPTIONAL
}

CG-ConfigInfo-v1730-IEs ::= SEQUENCE {
   fr1-Carriers-MCG-r17 [0] INTEGER (1..32) OPTIONAL,
   fr2-Carriers-MCG-r17 [1] INTEGER (1..32) OPTIONAL,
   nonCriticalExtension [2] CG-ConfigInfo-v1800-IEs OPTIONAL
}

CG-ConfigInfo-v1700-IEs ::= SEQUENCE {
   candidateCellListCPC-r17 [0] CandidateCellListCPC-r17 OPTIONAL,
   twoPHRModeMCG-r17 [1] ENUMERATED { enabled(0) } OPTIONAL,
   lowMobilityEvaluationConnectedInPCell-r17 [2] ENUMERATED { enabled(0) }
       OPTIONAL,
   nonCriticalExtension [3] CG-ConfigInfo-v1730-IEs OPTIONAL
}

CG-ConfigInfo-v1640-IEs ::= SEQUENCE {
   servCellInfoListMCG-NR-r16 [0] ServCellInfoListMCG-NR-r16 OPTIONAL,
   servCellInfoListMCG-EUTRA-r16 [1] ServCellInfoListMCG-EUTRA-r16 OPTIONAL,
   nonCriticalExtension [2] CG-ConfigInfo-v1700-IEs OPTIONAL
}

CG-ConfigInfo-v1620-IEs ::= SEQUENCE {
   ueAssistanceInformationSourceSCG-r16 [0] OCTET STRING (CONTAINING 
      UEAssistanceInformation) OPTIONAL,
   nonCriticalExtension [1] CG-ConfigInfo-v1640-IEs OPTIONAL
}

CG-ConfigInfo-v1610-IEs ::= SEQUENCE {
   drx-InfoMCG2 [0] DRX-Info2 OPTIONAL,
   alignedDRX-Indication [1] ENUMERATED { true(0) } OPTIONAL,
   scgFailureInfo-r16 [2] SEQUENCE {
      failureType-r16 [0] ENUMERATED { scg-lbtFailure-r16(0), 
         beamFailureRecoveryFailure-r16(1), t312-Expiry-r16(2), bh-RLF-r16(3), 
         beamFailure-r17(4), spare3(5), spare2(6), spare1(7) },
      measResultSCG-r16 [1] OCTET STRING (CONTAINING MeasResultSCG-Failure)
   } OPTIONAL,
   dummy1 [3] SEQUENCE {
      failureTypeEUTRA-r16 [0] ENUMERATED { scg-lbtFailure-r16(0), 
         beamFailureRecoveryFailure-r16(1), t312-Expiry-r16(2), spare5(3), 
         spare4(4), spare3(5), spare2(6), spare1(7) },
      measResultSCG-EUTRA-r16 [1] OCTET STRING
   } OPTIONAL,
   sidelinkUEInformationNR-r16 [4] OCTET STRING (CONTAINING 
      SidelinkUEInformationNR-r16) OPTIONAL,
   sidelinkUEInformationEUTRA-r16 [5] OCTET STRING OPTIONAL,
   nonCriticalExtension [6] CG-ConfigInfo-v1620-IEs OPTIONAL
}

CG-ConfigInfo-v1590-IEs ::= SEQUENCE {
   servFrequenciesMN-NR [0] SEQUENCE (SIZE (1..maxNrofServingCells-1)) OF ARFCN-ValueNR OPTIONAL,
   nonCriticalExtension [1] CG-ConfigInfo-v1610-IEs OPTIONAL
}

CG-ConfigInfo-v1570-IEs ::= SEQUENCE {
   sftdFrequencyList-NR [0] SFTD-FrequencyList-NR OPTIONAL,
   sftdFrequencyList-EUTRA [1] SFTD-FrequencyList-EUTRA OPTIONAL,
   nonCriticalExtension [2] CG-ConfigInfo-v1590-IEs OPTIONAL
}

CG-ConfigInfo-v1560-IEs ::= SEQUENCE {
   candidateCellInfoListMN-EUTRA [0] OCTET STRING OPTIONAL,
   candidateCellInfoListSN-EUTRA [1] OCTET STRING OPTIONAL,
   sourceConfigSCG-EUTRA [2] OCTET STRING OPTIONAL,
   scgFailureInfoEUTRA [3] SEQUENCE {
      failureTypeEUTRA [0] ENUMERATED { t313-Expiry(0), randomAccessProblem(1)
         , rlc-MaxNumRetx(2), scg-ChangeFailure(3) },
      measResultSCG-EUTRA [1] OCTET STRING
   } OPTIONAL,
   drx-ConfigMCG [4] DRX-Config OPTIONAL,
   measResultReportCGI-EUTRA [5] SEQUENCE {
      eutraFrequency [0] ARFCN-ValueEUTRA,
      cellForWhichToReportCGI-EUTRA [1] EUTRA-PhysCellId,
      cgi-InfoEUTRA [2] CGI-InfoEUTRA
   } OPTIONAL,
   measResultCellListSFTD-EUTRA [6] MeasResultCellListSFTD-EUTRA OPTIONAL,
   fr-InfoListMCG [7] FR-InfoList OPTIONAL,
   nonCriticalExtension [8] CG-ConfigInfo-v1570-IEs OPTIONAL
}

CG-ConfigInfo-v1540-IEs ::= SEQUENCE {
   ph-InfoMCG [0] PH-TypeListMCG OPTIONAL,
   measResultReportCGI [1] SEQUENCE {
      ssbFrequency [0] ARFCN-ValueNR,
      cellForWhichToReportCGI [1] PhysCellId,
      cgi-Info [2] CGI-InfoNR
   } OPTIONAL,
   nonCriticalExtension [2] CG-ConfigInfo-v1560-IEs OPTIONAL
}

CG-ConfigInfo-IEs ::= SEQUENCE {
   ue-CapabilityInfo [0] OCTET STRING (CONTAINING 
      UE-CapabilityRAT-ContainerList) OPTIONAL, -- Cond SN-AddMod
   candidateCellInfoListMN [1] MeasResultList2NR OPTIONAL,
   candidateCellInfoListSN [2] OCTET STRING (CONTAINING MeasResultList2NR)
       OPTIONAL,
   measResultCellListSFTD-NR [3] MeasResultCellListSFTD-NR OPTIONAL,
   scgFailureInfo [4] SEQUENCE {
      failureType [0] ENUMERATED { t310-Expiry(0), randomAccessProblem(1), 
         rlc-MaxNumRetx(2), synchReconfigFailure-SCG(3), scg-reconfigFailure(4)
         , srb3-IntegrityFailure(5) },
      measResultSCG [1] OCTET STRING (CONTAINING MeasResultSCG-Failure)
   } OPTIONAL,
   configRestrictInfo [5] ConfigRestrictInfoSCG OPTIONAL,
   drx-InfoMCG [6] DRX-Info OPTIONAL,
   measConfigMN [7] MeasConfigMN OPTIONAL,
   sourceConfigSCG [8] OCTET STRING (CONTAINING RRCReconfiguration) OPTIONAL,
   scg-RB-Config [9] OCTET STRING (CONTAINING RadioBearerConfig) OPTIONAL,
   mcg-RB-Config [10] OCTET STRING (CONTAINING RadioBearerConfig) OPTIONAL,
   mrdc-AssistanceInfo [11] MRDC-AssistanceInfo OPTIONAL,
   nonCriticalExtension [12] CG-ConfigInfo-v1540-IEs OPTIONAL
}

-- TAG-CG-CONFIG-STOP
-- TAG-CG-CONFIG-INFO-START
CG-ConfigInfo ::= SEQUENCE {
   criticalExtensions [0] EXPLICIT CHOICE {
      c1 [0] EXPLICIT CHOICE {
         cg-ConfigInfo [0] CG-ConfigInfo-IEs,
         spare3 [1] NULL,
         spare2 [2] NULL,
         spare1 [3] NULL
      },
      criticalExtensionsFuture [1] SEQUENCE {

      }
   }
}

MeasTiming ::= SEQUENCE {
   frequencyAndTiming [0] SEQUENCE {
      carrierFreq [0] ARFCN-ValueNR,
      ssbSubcarrierSpacing [1] SubcarrierSpacing,
      ssb-MeasurementTimingConfiguration [2] SSB-MTC,
      ss-RSSI-Measurement [3] SS-RSSI-Measurement OPTIONAL
   } OPTIONAL,
   ...,
   [[
      ssb-ToMeasure [1] EXPLICIT SSB-ToMeasure OPTIONAL,
      physCellId [2] PhysCellId OPTIONAL
   ]]
}

MeasTimingList ::= SEQUENCE (SIZE (1..maxMeasFreqsMN)) OF MeasTiming

MeasurementTimingConfiguration-v1610-IEs ::= SEQUENCE {
   csi-RS-Config-r16 [0] SEQUENCE {
      csi-RS-SubcarrierSpacing-r16 [0] SubcarrierSpacing,
      csi-RS-CellMobility-r16 [1] CSI-RS-CellMobility,
      refSSBFreq-r16 [2] ARFCN-ValueNR
   },
   nonCriticalExtension [1] SEQUENCE {

   } OPTIONAL
}

MeasurementTimingConfiguration-v1550-IEs ::= SEQUENCE {
   campOnFirstSSB [0] BOOLEAN,
   psCellOnlyOnFirstSSB [1] BOOLEAN,
   nonCriticalExtension [2] MeasurementTimingConfiguration-v1610-IEs OPTIONAL
}

MeasurementTimingConfiguration-IEs ::= SEQUENCE {
   measTiming [0] MeasTimingList OPTIONAL,
   nonCriticalExtension [1] MeasurementTimingConfiguration-v1550-IEs OPTIONAL
}

-- TAG-CG-CONFIG-INFO-STOP
-- TAG-MEASUREMENT-TIMING-CONFIGURATION-START
MeasurementTimingConfiguration ::= SEQUENCE {
   criticalExtensions [0] EXPLICIT CHOICE {
      c1 [0] EXPLICIT CHOICE {
         measTimingConf [0] MeasurementTimingConfiguration-IEs,
         spare3 [1] NULL,
         spare2 [2] NULL,
         spare1 [3] NULL
      },
      criticalExtensionsFuture [1] SEQUENCE {

      }
   }
}

UERadioPagingInformation-v1840-IEs ::= SEQUENCE {
   dl-SchedulingOffset-PDSCH-TypeA-FDD-FR2-NTN-r18 [0] ENUMERATED { 
      supported(0) } OPTIONAL,
   dl-SchedulingOffset-PDSCH-TypeB-FDD-FR2-NTN-r18 [1] ENUMERATED { 
      supported(0) } OPTIONAL,
   nonCriticalExtension [2] SEQUENCE {

   } OPTIONAL
}

UERadioPagingInformation-v1800-IEs ::= SEQUENCE {
   numberOfRxERedCap-r18 [0] ENUMERATED { one(0), two(1) } OPTIONAL,
   supportOf2RxXR-r18 [1] ENUMERATED { supported(0) } OPTIONAL,
   nonCriticalExtension [2] UERadioPagingInformation-v1840-IEs OPTIONAL
}

UERadioPagingInformation-v1700-IEs ::= SEQUENCE {
   ue-RadioPagingInfo-r17 [0] OCTET STRING (CONTAINING UE-RadioPagingInfo-r17)
       OPTIONAL,
   inactiveStatePO-Determination-r17 [1] ENUMERATED { supported(0) } OPTIONAL,
   numberOfRxRedCap-r17 [2] ENUMERATED { one(0), two(1) } OPTIONAL,
   halfDuplexFDD-TypeA-RedCap-r17 [3] SEQUENCE (SIZE (1..maxBands)) OF 
      FreqBandIndicatorNR OPTIONAL,
   nonCriticalExtension [4] UERadioPagingInformation-v1800-IEs OPTIONAL
}

UERadioPagingInformation-v15e0-IEs ::= SEQUENCE {
   dl-SchedulingOffset-PDSCH-TypeA-FDD-FR1 [0] ENUMERATED { supported(0) }
       OPTIONAL,
   dl-SchedulingOffset-PDSCH-TypeA-TDD-FR1 [1] ENUMERATED { supported(0) }
       OPTIONAL,
   dl-SchedulingOffset-PDSCH-TypeA-TDD-FR2 [2] ENUMERATED { supported(0) }
       OPTIONAL,
   dl-SchedulingOffset-PDSCH-TypeB-FDD-FR1 [3] ENUMERATED { supported(0) }
       OPTIONAL,
   dl-SchedulingOffset-PDSCH-TypeB-TDD-FR1 [4] ENUMERATED { supported(0) }
       OPTIONAL,
   dl-SchedulingOffset-PDSCH-TypeB-TDD-FR2 [5] ENUMERATED { supported(0) }
       OPTIONAL,
   nonCriticalExtension [6] UERadioPagingInformation-v1700-IEs OPTIONAL
}

UERadioPagingInformation-IEs ::= SEQUENCE {
   supportedBandListNRForPaging [0] SEQUENCE (SIZE (1..maxBands)) OF FreqBandIndicatorNR
       OPTIONAL,
   nonCriticalExtension [1] UERadioPagingInformation-v15e0-IEs OPTIONAL
}

-- TAG-MEASUREMENT-TIMING-CONFIGURATION-STOP
-- TAG-UE-RADIO-PAGING-INFORMATION-START
UERadioPagingInformation ::= SEQUENCE {
   criticalExtensions [0] EXPLICIT CHOICE {
      c1 [0] EXPLICIT CHOICE {
         ueRadioPagingInformation [0] UERadioPagingInformation-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

UERadioAccessCapabilityInformation-IEs ::= SEQUENCE {
   ue-RadioAccessCapabilityInfo [0] OCTET STRING (CONTAINING 
      UE-CapabilityRAT-ContainerList),
   nonCriticalExtension [1] SEQUENCE {

   } OPTIONAL
}

-- TAG-UE-RADIO-PAGING-INFORMATION-STOP
-- TAG-UE-RADIO-ACCESS-CAPABILITY-INFORMATION-START
UERadioAccessCapabilityInformation ::= SEQUENCE {
   criticalExtensions [0] EXPLICIT CHOICE {
      c1 [0] EXPLICIT CHOICE {
         ueRadioAccessCapabilityInformation [0] 
            UERadioAccessCapabilityInformation-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

-- Value assignments

maxMeasFreqsMN INTEGER ::= 32

maxMeasFreqsSN INTEGER ::= 32

maxMeasIdentitiesMN INTEGER ::= 62

maxCellPrep INTEGER ::= 32

maxNrofL1-MeasNoGap-r18 INTEGER ::= 8

maxNrofL1-MeasWithGap-r18 INTEGER ::= 8

maxNrofCellsL1-MeasNoGap-r18 INTEGER ::= 8

maxNrofCellsL1-MeasWithGap-r18 INTEGER ::= 8

maxNrofTotalCellsL1-MeasNoGap-r18 INTEGER ::= 24

maxNrofSSBsL1-MeasNoGap-r18 INTEGER ::= 8

maxNrofSSBsL1-MeasNoGapExt-r18 INTEGER ::= 24

maxNrofSSBsL1-MeasWithGap-r18 INTEGER ::= 8

maxNrofTotalSSBsL1-MeasNoGap-r18 INTEGER ::= 64

maxNrofSSBsL1-MeasIntraFreq-r18 INTEGER ::= 8

maxNrofSSBsL1-MeasInterFreq-r18 INTEGER ::= 8

maxNrofReportConfigsAperiodic-r18 INTEGER ::= 4

maxNrofReportConfigsPeriodic-r18 INTEGER ::= 4

maxNrofReportConfigsSemiPersistent-r18 INTEGER ::= 4

maxNrofCellsTA-Meas-r18 INTEGER ::= 8

maxNrofConfigJointTCI-States-r18 INTEGER ::= 128

maxNrofConfigDL-TCI-States-r18 INTEGER ::= 128

maxNrofConfigUL-TCI-States-r18 INTEGER ::= 64

maxNrofCellsTCI-r18 INTEGER ::= 8

maxNrofStoredConfigCells-r18 INTEGER ::= 16

maxNrofConfigCells-r18 INTEGER ::= 4

maxNrofActivatedJointTCI-States-r18 INTEGER ::= 32

maxNrofActivatedDL-TCI-States-r18 INTEGER ::= 32

maxNrofActivatedUL-TCI-States-r18 INTEGER ::= 32


END
