PC5-RRC-Definitions DEFINITIONS AUTOMATIC TAGS ::= BEGIN

IMPORTS

ARFCN-ValueNR, CellAccessRelatedInfo, SetupRelease, RRC-TransactionIdentifier, 
   SN-FieldLengthAM, SN-FieldLengthUM, LogicalChannelIdentity, maxNrofSLRB-r16
   , maxNrofSL-RxInfoSet-r17, maxNrofSL-QFIs-r16, maxNrofSL-QFIsPerDest-r16, 
   PagingCycle, PagingRecord, RSRP-Range, SL-MeasConfig-r16, SL-MeasId-r16, 
   FreqBandList, FreqBandIndicatorNR, GNSS-ID-r16, maxNrofRelayMeas-r17, 
   maxSimultaneousBands, maxBandComb, maxBands, maxSIB, maxSIB-MessagePlus1-r17
   , maxSL-LCID-r16, maxNrofFreqSL-1-r18, BandParametersSidelink-r16, 
   PagingRecord-v1700, RLC-ParametersSidelink-r16, SBAS-ID-r16, SIB1, 
   SL-DRX-ConfigUC-r17, SL-DRX-ConfigUC-SemiStatic-r17, 
   SL-PagingIdentityRemoteUE-r17, SL-RLC-ChannelID-r17, SL-SourceIdentity-r17, 
   SystemInformation, maxNrofSL-Dest-r16, SL-DestinationIdentity-r16, 
   SL-RelayIndicationMP-r18, SL-RSRP-Range-r16, SL-QoS-FlowIdentity-r16, 
   SL-QoS-Info-r16, maxNrofPhysicalResourceBlocks, SubcarrierSpacing
FROM NR-RRC-Definitions ;

-- Productions

SL-SIB-ReqInfo-r17 ::= ENUMERATED { sib1(0), sib2(1), sib3(2), sib4(3), sib5(4)
   , sib6(5), sib7(6), sib8(7), sib9(8), sib10(9), sib11(10), sib12(11), 
   sib13(12), sib14(13), sib15(14), sib16(15), sib17(16), sib18(17), sib19(18)
   , sib20(19), sib21(20), sibNotReq11(21), sibNotReq10(22), sibNotReq9(23), 
   sibNotReq8(24), sibNotReq7(25), sibNotReq6(26), sibNotReq5(27), 
   sibNotReq4(28), sibNotReq3(29), sibNotReq2(30), sibNotReq1(31), ..., 
   sib17bis-v1820(32) }

SL-CarrierId-r18 ::= INTEGER (1..maxNrofFreqSL-1-r18)

SL-RLC-BearerConfigIndex-r18 ::= INTEGER (1..maxSL-LCID-r16)

SL-LatencyBoundIUC-Report-r17 ::= INTEGER (3..160)

SLRB-PC5-ConfigIndex-r16 ::= INTEGER (1..maxNrofSLRB-r16)

SL-PQFI-r16 ::= INTEGER (1..64)

AccessStratumReleaseSidelink-r16 ::= ENUMERATED { rel16(0), rel17(1), rel18(2)
   , spare5(3), spare4(4), spare3(5), spare2(6), spare1(7), ... }

-- TAG-SCCH-MESSAGE-STOP
-- TAG-MASTERINFORMATIONBLOCKSIDELINK-START
MasterInformationBlockSidelink ::= SEQUENCE {
   sl-TDD-Config-r16 [0] BIT STRING  (SIZE (12)),
   inCoverage-r16 [1] BOOLEAN,
   directFrameNumber-r16 [2] BIT STRING  (SIZE (10)),
   slotIndex-r16 [3] BIT STRING  (SIZE (7)),
   reservedBits-r16 [4] BIT STRING  (SIZE (2))
}

SBCCH-SL-BCH-MessageType ::= CHOICE {
   c1 [0] EXPLICIT CHOICE {
      masterInformationBlockSidelink [0] MasterInformationBlockSidelink,
      spare1 [1] NULL
   },
   messageClassExtension [1] SEQUENCE {

   }
}

-- TAG-PC5-RRC-DEFINITIONS-STOP
-- TAG-SBCCH-SL-BCH-MESSAGE-START
SBCCH-SL-BCH-Message ::= SEQUENCE {
   message [0] EXPLICIT SBCCH-SL-BCH-MessageType
}

SL-MeasQuantityResult-r16 ::= SEQUENCE {
   sl-RSRP-r16 [0] RSRP-Range OPTIONAL,
   ...,
   [[
      sl-RSRP-DedicatedSL-PRS-RP-r18 [1] SL-RSRP-Range-r16 OPTIONAL
   ]]
}

SL-MeasResult-r16 ::= SEQUENCE {
   sl-ResultDMRS-r16 [0] SL-MeasQuantityResult-r16 OPTIONAL,
   ...,
   [[
      sl-Result-SL-PRS-r18 [1] SL-MeasQuantityResult-r16 OPTIONAL
   ]]
}

SL-MeasResults-r16 ::= SEQUENCE {
   sl-MeasId-r16 [0] SL-MeasId-r16,
   sl-MeasResult-r16 [1] SL-MeasResult-r16,
   ...
}

MeasurementReportSidelink-r16-IEs ::= SEQUENCE {
   sl-MeasResults-r16 [0] SL-MeasResults-r16,
   lateNonCriticalExtension [1] OCTET STRING OPTIONAL,
   nonCriticalExtension [2] SEQUENCE {

   } OPTIONAL
}

-- TAG-MASTERINFORMATIONBLOCKSIDELINK-STOP
-- TAG-MEASUREMENTREPORTSIDELINK-START
MeasurementReportSidelink ::= SEQUENCE {
   criticalExtensions [0] EXPLICIT CHOICE {
      measurementReportSidelink-r16 [0] MeasurementReportSidelink-r16-IEs,
      criticalExtensionsFuture [1] SEQUENCE {

      }
   }
}

SL-SDAP-ConfigPC5-r16 ::= SEQUENCE {
   sl-MappedQoS-FlowsToAddList-r16 [0] SEQUENCE (SIZE (1..maxNrofSL-QFIsPerDest-r16)) OF SL-PQFI-r16
       OPTIONAL, -- Need N
   sl-MappedQoS-FlowsToReleaseList-r16 [1] SEQUENCE (SIZE (1..maxNrofSL-QFIsPerDest-r16)) OF SL-PQFI-r16
       OPTIONAL, -- Need N
   sl-SDAP-Header-r16 [2] ENUMERATED { present(0), absent(1) },
   ...
}

SL-PDCP-ConfigPC5-r16 ::= SEQUENCE {
   sl-PDCP-SN-Size-r16 [0] ENUMERATED { len12bits(0), len18bits(1) } OPTIONAL, -- Need M
   sl-OutOfOrderDelivery-r16 [1] ENUMERATED { true(0) } OPTIONAL,
   ...
}

SL-RLC-ConfigPC5-r16 ::= CHOICE {
   sl-AM-RLC-r16 [0] SEQUENCE {
      sl-SN-FieldLengthAM-r16 [0] SN-FieldLengthAM OPTIONAL,
      ...
   },
   sl-UM-Bi-Directional-RLC-r16 [1] SEQUENCE {
      sl-SN-FieldLengthUM-r16 [0] SN-FieldLengthUM OPTIONAL,
      ...
   },
   sl-UM-Uni-Directional-RLC-r16 [2] SEQUENCE {
      sl-SN-FieldLengthUM-r16 [0] SN-FieldLengthUM OPTIONAL,
      ...
   }
}

SL-LogicalChannelConfigPC5-r16 ::= SEQUENCE {
   sl-LogicalChannelIdentity-r16 [0] LogicalChannelIdentity,
   ...,
   [[
      sl-LogicalChannelIdentity-v1800 [1] INTEGER (33..38) OPTIONAL
   ]]
}

SLRB-Config-r16 ::= SEQUENCE {
   slrb-PC5-ConfigIndex-r16 [0] SLRB-PC5-ConfigIndex-r16,
   sl-SDAP-ConfigPC5-r16 [1] SL-SDAP-ConfigPC5-r16 OPTIONAL, -- Need M
   sl-PDCP-ConfigPC5-r16 [2] SL-PDCP-ConfigPC5-r16 OPTIONAL, -- Need M
   sl-RLC-ConfigPC5-r16 [3] EXPLICIT SL-RLC-ConfigPC5-r16 OPTIONAL, -- Need M
   sl-MAC-LogicalChannelConfigPC5-r16 [4] SL-LogicalChannelConfigPC5-r16
       OPTIONAL,
   ...
}

SL-CSI-RS-Config-r16 ::= SEQUENCE {
   sl-CSI-RS-FreqAllocation-r16 [0] EXPLICIT CHOICE {
      sl-OneAntennaPort-r16 [0] BIT STRING  (SIZE (12)),
      sl-TwoAntennaPort-r16 [1] BIT STRING  (SIZE (6))
   } OPTIONAL, -- Need M
   sl-CSI-RS-FirstSymbol-r16 [1] INTEGER (3..12) OPTIONAL,
   ...
}

SL-RLC-ChannelConfigPC5-r17 ::= SEQUENCE {
   sl-RLC-ChannelID-PC5-r17 [0] SL-RLC-ChannelID-r17,
   sl-RLC-ConfigPC5-r17 [1] EXPLICIT SL-RLC-ConfigPC5-r16 OPTIONAL, -- Need M
   sl-MAC-LogicalChannelConfigPC5-r17 [2] SL-LogicalChannelConfigPC5-r16
       OPTIONAL,
   ...
}

SL-SFN-DFN-Offset-r18 ::= SEQUENCE {
   sl-FrameOffset-r18 [0] INTEGER (0..1023),
   sl-SubframeOffset-r18 [1] INTEGER (0..9),
   sl-SlotOffset-r18 [2] INTEGER (0..31)
}

SL-CarrierConfig-r18 ::= SEQUENCE {
   sl-CarrierId-r18 [0] SL-CarrierId-r18,
   sl-OffsetToCarrier-r18 [1] INTEGER (0..2199),
   subcarrierSpacing-r18 [2] SubcarrierSpacing,
   carrierBandwidth-r18 [3] INTEGER (1..maxNrofPhysicalResourceBlocks),
   sl-AbsoluteFrequencyPointA-r18 [4] ARFCN-ValueNR
}

SL-RLC-BearerConfig-r18 ::= CHOICE {
   srb [0] SEQUENCE {
      sl-SRB-IdentityWithDuplication [0] INTEGER (1..3),
      sL-RLC-BearerConfigIndex-r18 [1] SL-RLC-BearerConfigIndex-r18,
      ...
   },
   drb [1] SEQUENCE {
      slrb-PC5-ConfigIndex-r18 [0] SLRB-PC5-ConfigIndex-r16,
      sL-RLC-BearerConfigIndex-r18 [1] SL-RLC-BearerConfigIndex-r18,
      sl-RLC-ConfigPC5-r18 [2] EXPLICIT SL-RLC-ConfigPC5-r16 OPTIONAL, -- Need M
      sl-MAC-LogicalChannelConfigPC5-r18 [3] SL-LogicalChannelConfigPC5-r16
          OPTIONAL,
      ...
   }
}

SL-SRAP-ConfigPC5-r18 ::= SEQUENCE {
   sl-PeerRemoteUE-L2Identity-r18 [0] SL-DestinationIdentity-r16 OPTIONAL, -- Need M
   sl-PeerRemoteUE-LocalIdentity-r18 [1] INTEGER (0..255) OPTIONAL, -- Need M
   sl-RemoteUE-L2Identity-r18 [2] SL-SourceIdentity-r17 OPTIONAL, -- Need M
   sl-RemoteUE-LocalIdentity-r18 [3] INTEGER (0..255) OPTIONAL,
   ...
}

RRCReconfigurationSidelink-v1800-IEs ::= SEQUENCE {
   sl-SFN-DFN-Offset-r18 [0] EXPLICIT CHOICE {
      release [0] NULL,
      setup [1] EXPLICIT SL-SFN-DFN-Offset-r18
   } OPTIONAL, -- Need M
   sl-CarrierToAddModList-r18 [1] SEQUENCE (SIZE (1..maxNrofFreqSL-1-r18)) OF SL-CarrierConfig-r18
       OPTIONAL, -- Need N
   sl-CarrierToReleaseList-r18 [2] SEQUENCE (SIZE (1..maxNrofFreqSL-1-r18)) OF SL-CarrierId-r18
       OPTIONAL, -- Need N
   sl-RLC-BearerToAddModList-r18 [3] SEQUENCE (SIZE (1..maxNrofSLRB-r16)) OF 
      SL-RLC-BearerConfig-r18 OPTIONAL, -- Need N
   sl-RLC-BearerToReleaseList-r18 [4] SEQUENCE (SIZE (1..maxNrofSLRB-r16)) OF 
      SL-RLC-BearerConfigIndex-r18 OPTIONAL, -- Need N
   sl-LocalID-PairList-r18 [5] SEQUENCE (SIZE (1..maxNrofSL-Dest-r16)) OF SL-SRAP-ConfigPC5-r18
       OPTIONAL, -- Need N
   nonCriticalExtension [6] SEQUENCE {

   } OPTIONAL
}

RRCReconfigurationSidelink-v1700-IEs ::= SEQUENCE {
   sl-DRX-ConfigUC-PC5-r17 [0] EXPLICIT CHOICE {
      release [0] NULL,
      setup [1] EXPLICIT SL-DRX-ConfigUC-r17
   } OPTIONAL, -- Need M
   sl-LatencyBoundIUC-Report-r17 [1] EXPLICIT CHOICE {
      release [0] NULL,
      setup [1] EXPLICIT SL-LatencyBoundIUC-Report-r17
   } OPTIONAL, -- Need M
   sl-RLC-ChannelToReleaseListPC5-r17 [2] SEQUENCE (SIZE (1..maxSL-LCID-r16)) OF 
      SL-RLC-ChannelID-r17 OPTIONAL, -- Need N
   sl-RLC-ChannelToAddModListPC5-r17 [3] SEQUENCE (SIZE (1..maxSL-LCID-r16)) OF 
      SL-RLC-ChannelConfigPC5-r17 OPTIONAL, -- Need N
   nonCriticalExtension [4] RRCReconfigurationSidelink-v1800-IEs OPTIONAL
}

RRCReconfigurationSidelink-r16-IEs ::= SEQUENCE {
   slrb-ConfigToAddModList-r16 [0] SEQUENCE (SIZE (1..maxNrofSLRB-r16)) OF SLRB-Config-r16
       OPTIONAL, -- Need N
   slrb-ConfigToReleaseList-r16 [1] SEQUENCE (SIZE (1..maxNrofSLRB-r16)) OF 
      SLRB-PC5-ConfigIndex-r16 OPTIONAL, -- Need N
   sl-MeasConfig-r16 [2] EXPLICIT CHOICE {
      release [0] NULL,
      setup [1] EXPLICIT SL-MeasConfig-r16
   } OPTIONAL, -- Need M
   sl-CSI-RS-Config-r16 [3] EXPLICIT CHOICE {
      release [0] NULL,
      setup [1] EXPLICIT SL-CSI-RS-Config-r16
   } OPTIONAL, -- Need M
   sl-ResetConfig-r16 [4] ENUMERATED { true(0) } OPTIONAL, -- Need N
   sl-LatencyBoundCSI-Report-r16 [5] INTEGER (3..160) OPTIONAL, -- Need M
   lateNonCriticalExtension [6] OCTET STRING OPTIONAL,
   nonCriticalExtension [7] RRCReconfigurationSidelink-v1700-IEs OPTIONAL
}

-- TAG-REMOTEUEINFORMATIONSIDELINK-STOP
-- TAG-RRCRECONFIGURATIONSIDELINK-START
RRCReconfigurationSidelink ::= SEQUENCE {
   rrc-TransactionIdentifier-r16 [0] RRC-TransactionIdentifier,
   criticalExtensions [1] EXPLICIT CHOICE {
      rrcReconfigurationSidelink-r16 [0] RRCReconfigurationSidelink-r16-IEs,
      criticalExtensionsFuture [1] SEQUENCE {

      }
   }
}

RRCReconfigurationCompleteSidelink-v1720-IEs ::= SEQUENCE {
   sl-DRX-ConfigReject-v1720 [0] ENUMERATED { true(0) } OPTIONAL,
   nonCriticalExtension [1] SEQUENCE {

   } OPTIONAL
}

RRCReconfigurationCompleteSidelink-v1710-IEs ::= SEQUENCE {
   dummy [0] ENUMERATED { true(0) },
   nonCriticalExtension [1] RRCReconfigurationCompleteSidelink-v1720-IEs
       OPTIONAL
}

RRCReconfigurationCompleteSidelink-r16-IEs ::= SEQUENCE {
   lateNonCriticalExtension [0] OCTET STRING OPTIONAL,
   nonCriticalExtension [1] RRCReconfigurationCompleteSidelink-v1710-IEs
       OPTIONAL
}

-- TAG-RRCRECONFIGURATIONSIDELINK-STOP
-- TAG-RRCRECONFIGURATIONCOMPLETESIDELINK-START
RRCReconfigurationCompleteSidelink ::= SEQUENCE {
   rrc-TransactionIdentifier-r16 [0] RRC-TransactionIdentifier,
   criticalExtensions [1] EXPLICIT CHOICE {
      rrcReconfigurationCompleteSidelink-r16 [0] 
         RRCReconfigurationCompleteSidelink-r16-IEs,
      criticalExtensionsFuture [1] SEQUENCE {

      }
   }
}

RRCReconfigurationFailureSidelink-r16-IEs ::= SEQUENCE {
   lateNonCriticalExtension [0] OCTET STRING OPTIONAL,
   nonCriticalExtension [1] SEQUENCE {

   } OPTIONAL
}

-- TAG-RRCRECONFIGURATIONCOMPLETESIDELINK-STOP
-- TAG-RRCRECONFIGURATIONFAILURESIDELINK-START
RRCReconfigurationFailureSidelink ::= SEQUENCE {
   rrc-TransactionIdentifier-r16 [0] RRC-TransactionIdentifier,
   criticalExtensions [1] EXPLICIT CHOICE {
      rrcReconfigurationFailureSidelink-r16 [0] 
         RRCReconfigurationFailureSidelink-r16-IEs,
      criticalExtensionsFuture [1] SEQUENCE {

      }
   }
}

UECapabilityEnquirySidelink-r16-IEs ::= SEQUENCE {
   frequencyBandListFilterSidelink-r16 [0] FreqBandList OPTIONAL, -- Need N
   ue-CapabilityInformationSidelink-r16 [1] OCTET STRING OPTIONAL, -- Need N
   lateNonCriticalExtension [2] OCTET STRING OPTIONAL,
   nonCriticalExtension [3] SEQUENCE {

   } OPTIONAL
}

-- TAG-UEASSISTANCEINFORMATIONSIDELINK-STOP
-- TAG-UECAPABILITYENQUIRYSIDELINK-START
UECapabilityEnquirySidelink ::= SEQUENCE {
   rrc-TransactionIdentifier-r16 [0] RRC-TransactionIdentifier,
   criticalExtensions [1] EXPLICIT CHOICE {
      ueCapabilityEnquirySidelink-r16 [0] UECapabilityEnquirySidelink-r16-IEs,
      criticalExtensionsFuture [1] SEQUENCE {

      }
   }
}

PDCP-ParametersSidelink-r16 ::= SEQUENCE {
   outOfOrderDeliverySidelink-r16 [0] ENUMERATED { supported(0) } OPTIONAL,
   ...,
   [[
      pdcp-DuplicationSRB-sidelink-r18 [1] ENUMERATED { supported(0) } OPTIONAL
         ,
      pdcp-DuplicationDRB-sidelink-r18 [2] ENUMERATED { supported(0) } OPTIONAL
   ]]
}

BandCombinationParametersSidelinkNR-r16 ::= SEQUENCE (SIZE (1..maxSimultaneousBands)) OF 
   BandParametersSidelink-r16

BandCombinationListSidelinkNR-r16 ::= SEQUENCE (SIZE (1..maxBandComb)) OF 
   BandCombinationParametersSidelinkNR-r16

BandSidelinkPC5-r16 ::= SEQUENCE {
   freqBandSidelink-r16 [0] FreqBandIndicatorNR,
     --15-1
   sl-Reception-r16 [1] SEQUENCE {
      harq-RxProcessSidelink-r16 [0] ENUMERATED { n16(0), n24(1), n32(2), 
         n64(3) },
      pscch-RxSidelink-r16 [1] ENUMERATED { value1(0), value2(1) },
      scs-CP-PatternRxSidelink-r16 [2] EXPLICIT CHOICE {
         fr1-r16 [0] SEQUENCE {
            scs-15kHz-r16 [0] BIT STRING  (SIZE (16)) OPTIONAL,
            scs-30kHz-r16 [1] BIT STRING  (SIZE (16)) OPTIONAL,
            scs-60kHz-r16 [2] BIT STRING  (SIZE (16)) OPTIONAL
         },
         fr2-r16 [1] SEQUENCE {
            scs-60kHz-r16 [0] BIT STRING  (SIZE (16)) OPTIONAL,
            scs-120kHz-r16 [1] BIT STRING  (SIZE (16)) OPTIONAL
         }
      } OPTIONAL,
      extendedCP-RxSidelink-r16 [3] ENUMERATED { supported(0) } OPTIONAL
   } OPTIONAL,
     --15-10
   sl-Tx-256QAM-r16 [2] ENUMERATED { supported(0) } OPTIONAL,
     --15-12
   lowSE-64QAM-MCS-TableSidelink-r16 [3] ENUMERATED { supported(0) } OPTIONAL,
   ...,
   [[
      csi-ReportSidelink-r16 [4] SEQUENCE {
         csi-RS-PortsSidelink-r16 [0] ENUMERATED { p1(0), p2(1) }
      } OPTIONAL,
      rankTwoReception-r16 [5] ENUMERATED { supported(0) } OPTIONAL,
      sl-openLoopPC-RSRP-ReportSidelink-r16 [6] ENUMERATED { supported(0) }
          OPTIONAL,
      sl-Rx-256QAM-r16 [7] ENUMERATED { supported(0) } OPTIONAL
   ]],
   [[
      rx-IUC-Scheme1-PreferredMode2Sidelink-r17 [8] ENUMERATED { supported(0) }
          OPTIONAL,
      rx-IUC-Scheme1-NonPreferredMode2Sidelink-r17 [9] ENUMERATED { 
         supported(0) } OPTIONAL,
      rx-IUC-Scheme2-Mode2Sidelink-r17 [10] ENUMERATED { n5(0), n15(1), n25(2)
         , n32(3), n35(4), n45(5), n50(6), n64(7) } OPTIONAL,
      rx-IUC-Scheme1-SCI-r17 [11] ENUMERATED { supported(0) } OPTIONAL,
      rx-IUC-Scheme1-SCI-ExplicitReq-r17 [12] ENUMERATED { supported(0) }
          OPTIONAL,
      scheme2-ConflictDeterminationRSRP-r17 [13] ENUMERATED { supported(0) }
          OPTIONAL
   ]],
   [[
      sl-PathlossBasedOLPC-SL-RSRP-Report-r18 [14] ENUMERATED { supported(0) }
          OPTIONAL,
      sl-UE-COT-Sharing-r18 [15] ENUMERATED { supported(0) } OPTIONAL,
      sl-PSFCH-MultiContiguousRB-r18 [16] ENUMERATED { supported(0) } OPTIONAL
         ,
      sl-PSFCH-MultiNonContiguousRB-r18 [17] ENUMERATED { supported(0) }
          OPTIONAL,
      sl-CA-Communication-r18 [18] SEQUENCE {
         numberOfCarriers-r18 [0] INTEGER (2..8),
         numberOfPSCCH-DecodeValueZ-r18 [1] INTEGER (1..2),
         totalBandwidth-r18 [2] ENUMERATED { mhz20(0), mhz30(1), mhz40(2), 
            mhz50(3), mhz60(4), mhz70(5) }
      } OPTIONAL,
      sl-ReceptionIntraCarrierGuardBand-r18 [19] ENUMERATED { supported(0) }
          OPTIONAL,
      sl-PowerClassUnlicensed-r18 [20] ENUMERATED { pc5(0), spare7(1), 
         spare6(2), spare5(3), spare4(4), spare3(5), spare2(6), spare1(7) }
          OPTIONAL
   ]]
}

MAC-ParametersSidelink-r17 ::= SEQUENCE {
   drx-OnSidelink-r17 [0] ENUMERATED { supported(0) } OPTIONAL,
   ...
}

BandParametersSidelink-v1710 ::= SEQUENCE {
     --32-5a-1
   tx-IUC-Scheme1-Mode2Sidelink-r17 [0] ENUMERATED { supported(0) } OPTIONAL,
     --32-5b-1
   tx-IUC-Scheme2-Mode2Sidelink-r17 [1] ENUMERATED { n4(0), n8(1), n16(2) }
       OPTIONAL
}

BandCombinationParametersSidelinkNR-v1710 ::= SEQUENCE (SIZE (1..maxSimultaneousBands)) OF 
   BandParametersSidelink-v1710

BandCombinationListSidelinkNR-v1710 ::= SEQUENCE (SIZE (1..maxBandComb)) OF 
   BandCombinationParametersSidelinkNR-v1710

UECapabilityInformationSidelink-v1800-IEs ::= SEQUENCE {
   sfn-DFN-OffsetSupported-r18 [0] ENUMERATED { supported(0) } OPTIONAL,
   posSIB-ForwardingSupported-r18 [1] ENUMERATED { supported(0) } OPTIONAL,
   nonCriticalExtension [2] SEQUENCE {

   } OPTIONAL
}

UECapabilityInformationSidelink-v1700-IEs ::= SEQUENCE {
   mac-ParametersSidelink-r17 [0] MAC-ParametersSidelink-r17 OPTIONAL,
   supportedBandCombinationListSidelinkNR-v1710 [1] 
      BandCombinationListSidelinkNR-v1710 OPTIONAL,
   nonCriticalExtension [2] UECapabilityInformationSidelink-v1800-IEs OPTIONAL
}

UECapabilityInformationSidelink-r16-IEs ::= SEQUENCE {
   accessStratumReleaseSidelink-r16 [0] AccessStratumReleaseSidelink-r16,
   pdcp-ParametersSidelink-r16 [1] PDCP-ParametersSidelink-r16 OPTIONAL,
   rlc-ParametersSidelink-r16 [2] RLC-ParametersSidelink-r16 OPTIONAL,
   supportedBandCombinationListSidelinkNR-r16 [3] 
      BandCombinationListSidelinkNR-r16 OPTIONAL,
   supportedBandListSidelink-r16 [4] SEQUENCE (SIZE (1..maxBands)) OF 
      BandSidelinkPC5-r16 OPTIONAL,
   appliedFreqBandListFilter-r16 [5] FreqBandList OPTIONAL,
   lateNonCriticalExtension [6] OCTET STRING OPTIONAL,
   nonCriticalExtension [7] UECapabilityInformationSidelink-v1700-IEs OPTIONAL
}

-- TAG-UECAPABILITYENQUIRYSIDELINK-STOP
-- TAG-UECAPABILITYINFORMATIONSIDELINK-START
UECapabilityInformationSidelink ::= SEQUENCE {
   rrc-TransactionIdentifier-r16 [0] RRC-TransactionIdentifier,
   criticalExtensions [1] EXPLICIT CHOICE {
      ueCapabilityInformationSidelink-r16 [0] 
         UECapabilityInformationSidelink-r16-IEs,
      criticalExtensionsFuture [1] SEQUENCE {

      }
   }
}

UuMessageTransferSidelink-v1800-IEs ::= SEQUENCE {
   sl-PagingDelivery-r18 [0] OCTET STRING (CONTAINING PagingRecord-v1700)
       OPTIONAL, -- Need N
   nonCriticalExtension [1] SEQUENCE {

   } OPTIONAL
}

UuMessageTransferSidelink-r17-IEs ::= SEQUENCE {
   sl-PagingDelivery-r17 [0] OCTET STRING (CONTAINING PagingRecord) OPTIONAL, -- Need N
   sl-SIB1-Delivery-r17 [1] OCTET STRING (CONTAINING SIB1) OPTIONAL, -- Need N
   sl-SystemInformationDelivery-r17 [2] OCTET STRING (CONTAINING 
      SystemInformation) OPTIONAL, -- Need N
   lateNonCriticalExtension [3] OCTET STRING OPTIONAL,
   nonCriticalExtension [4] UuMessageTransferSidelink-v1800-IEs OPTIONAL
}

-- TAG-UEINFORMATIONRESPONSESIDELINK-STOP
-- TAG-UUMESSAGETRANSFERSIDELINK-START
UuMessageTransferSidelink-r17 ::= SEQUENCE {
   criticalExtensions [0] EXPLICIT CHOICE {
      uuMessageTransferSidelink-r17 [0] UuMessageTransferSidelink-r17-IEs,
      criticalExtensionsFuture [1] SEQUENCE {

      }
   }
}

SL-RequestedSIB-List-r17 ::= SEQUENCE (SIZE (maxSIB-MessagePlus1-r17)) OF SL-SIB-ReqInfo-r17

SL-PagingInfo-RemoteUE-r17 ::= SEQUENCE {
   sl-PagingIdentityRemoteUE-r17 [0] SL-PagingIdentityRemoteUE-r17,
   sl-PagingCycleRemoteUE-r17 [1] PagingCycle OPTIONAL -- Need M
}

SL-PosSIB-ReqInfo-r18 ::= SEQUENCE {
   gnss-id-r18 [0] GNSS-ID-r16 OPTIONAL, -- Need R
   sbas-id-r18 [1] SBAS-ID-r16 OPTIONAL, -- Cond GNSS-ID-SBAS
   posSibType-r18 [2] ENUMERATED { posSibType1-1(0), posSibType1-2(1), 
      posSibType1-3(2), posSibType1-4(3), posSibType1-5(4), posSibType1-6(5), 
      posSibType1-7(6), posSibType1-8(7), posSibType1-9(8), posSibType1-10(9), 
      posSibType1-11(10), posSibType1-12(11), posSibType2-1(12), 
      posSibType2-2(13), posSibType2-3(14), posSibType2-4(15), 
      posSibType2-5(16), posSibType2-6(17), posSibType2-7(18), 
      posSibType2-8(19), posSibType2-9(20), posSibType2-10(21), 
      posSibType2-11(22), posSibType2-12(23), posSibType2-13(24), 
      posSibType2-14(25), posSibType2-15(26), posSibType2-16(27), 
      posSibType2-17(28), posSibType2-17a(29), posSibType2-18(30), 
      posSibType2-18a(31), posSibType2-19(32), posSibType2-20(33), 
      posSibType2-20a(34), posSibType2-21(35), posSibType2-22(36), 
      posSibType2-23(37), posSibType2-24(38), posSibType2-25(39), 
      posSibType2-26(40), posSibType2-27(41), posSibType3-1(42), 
      posSibType4-1(43), posSibType5-1(44), posSibType6-1(45), 
      posSibType6-2(46), posSibType6-3(47), posSibType6-4(48), 
      posSibType6-5(49), posSibType6-6(50), posSibType6-7(51), 
      posSibType7-1(52), posSibType7-2(53), posSibType7-3(54), 
      posSibType7-4(55), spare9(56), spare8(57), spare7(58), spare6(59), 
      spare5(60), spare4(61), spare3(62), spare2(63), spare1(64), ... }
}

SL-RequestedPosSIB-List-r18 ::= SEQUENCE (SIZE (1..maxSIB)) OF SL-PosSIB-ReqInfo-r18

RemoteUEInformationSidelink-v1800-IEs ::= SEQUENCE {
   sl-RequestedPosSIB-List-r18 [0] EXPLICIT CHOICE {
      release [0] NULL,
      setup [1] EXPLICIT SL-RequestedPosSIB-List-r18
   } OPTIONAL, -- Need M
   sl-SFN-DFN-OffsetRequested-r18 [1] ENUMERATED { true(0) } OPTIONAL, -- Need R
   connectionForMP-r18 [2] ENUMERATED { true(0) } OPTIONAL, -- Need N
   sl-DestinationIdentityRemoteUE-r18 [3] SL-DestinationIdentity-r16 OPTIONAL, -- Need N
   nonCriticalExtension [4] SEQUENCE {

   } OPTIONAL
}

RemoteUEInformationSidelink-r17-IEs ::= SEQUENCE {
   sl-RequestedSIB-List-r17 [0] EXPLICIT CHOICE {
      release [0] NULL,
      setup [1] EXPLICIT SL-RequestedSIB-List-r17
   } OPTIONAL, -- Need M
   sl-PagingInfo-RemoteUE-r17 [1] EXPLICIT CHOICE {
      release [0] NULL,
      setup [1] EXPLICIT SL-PagingInfo-RemoteUE-r17
   } OPTIONAL, -- Need M
   lateNonCriticalExtension [2] OCTET STRING OPTIONAL,
   nonCriticalExtension [3] RemoteUEInformationSidelink-v1800-IEs OPTIONAL
}

-- TAG-NOTIFICATIONMESSAGESIDELINK -STOP
-- TAG-REMOTEUEINFORMATIONSIDELINK-START
RemoteUEInformationSidelink-r17 ::= SEQUENCE {
   criticalExtensions [0] EXPLICIT CHOICE {
      remoteUEInformationSidelink-r17 [0] RemoteUEInformationSidelink-r17-IEs,
      criticalExtensionsFuture [1] SEQUENCE {

      }
   }
}

NotificationMessageSidelink-v1800-IEs ::= SEQUENCE {
   sl-IndicationType-r18 [0] ENUMERATED { relayUE-PC5-RLF(0), spare1(1) }
       OPTIONAL, -- Need N
   sl-DestinationIdentityRemoteUE-r18 [1] SL-DestinationIdentity-r16 OPTIONAL, -- Need N
   nonCriticalExtension [2] SEQUENCE {

   } OPTIONAL
}

NotificationMessageSidelink-r17-IEs ::= SEQUENCE {
   indicationType-r17 [0] ENUMERATED { relayUE-Uu-RLF(0), relayUE-HO(1), 
      relayUE-CellReselection(2), relayUE-Uu-RRC-Failure(3) } OPTIONAL, -- Need N
   lateNonCriticalExtension [1] OCTET STRING OPTIONAL,
   nonCriticalExtension [2] NotificationMessageSidelink-v1800-IEs OPTIONAL
}

-- TAG-MEASUREMENTREPORTSIDELINK-STOP
-- TAG-NOTIFICATIONMESSAGESIDELINK-START
NotificationMessageSidelink-r17 ::= SEQUENCE {
   criticalExtensions [0] EXPLICIT CHOICE {
      notificationMessageSidelink-r17 [0] NotificationMessageSidelink-r17-IEs,
      criticalExtensionsFuture [1] SEQUENCE {

      }
   }
}

UEAssistanceInformationSidelink-r17-IEs ::= SEQUENCE {
   sl-PreferredDRX-ConfigList-r17 [0] SEQUENCE (SIZE (1..maxNrofSL-RxInfoSet-r17)) OF 
      SL-DRX-ConfigUC-SemiStatic-r17 OPTIONAL,
                                                                                                                   -- Need R
   lateNonCriticalExtension [1] OCTET STRING OPTIONAL,
   nonCriticalExtension [2] SEQUENCE {

   } OPTIONAL
}

-- TAG-RRCRECONFIGURATIONFAILURESIDELINK-STOP
-- TAG-UEASSISTANCEINFORMATIONSIDELINK-START
UEAssistanceInformationSidelink-r17 ::= SEQUENCE {
   criticalExtensions [0] EXPLICIT CHOICE {
      ueAssistanceInformationSidelink-r17 [0] 
         UEAssistanceInformationSidelink-r17-IEs,
      criticalExtensionsFuture [1] SEQUENCE {

      }
   }
}

SL-E2E-QoS-InfoPC5-r18 ::= SEQUENCE {
   sl-DestinationIdentityRemoteUE-r18 [0] SL-DestinationIdentity-r16,
   sl-E2E-SLRB-Index-r18 [1] SLRB-PC5-ConfigIndex-r16,
   sl-QoS-InfoList-r18 [2] SEQUENCE (SIZE (1..maxNrofSL-QFIsPerDest-r16)) OF SL-QoS-Info-r16
}

UEInformationRequestSidelink-r18-IEs ::= SEQUENCE {
   sl-E2E-QoS-InfoListPC5-r18 [0] SEQUENCE (SIZE (1..maxNrofSLRB-r16)) OF 
      SL-E2E-QoS-InfoPC5-r18 OPTIONAL, -- Need N
   lateNonCriticalExtension [1] OCTET STRING OPTIONAL,
   nonCriticalExtension [2] SEQUENCE {

   } OPTIONAL
}

-- TAG-UECAPABILITYINFORMATIONSIDELINK-STOP
-- TAG-UEINFORMATIONREQUESTSIDELINK-START
UEInformationRequestSidelink-r18 ::= SEQUENCE {
   rrc-TransactionIdentifier-r18 [0] RRC-TransactionIdentifier,
   criticalExtensions [1] EXPLICIT CHOICE {
      ueInformationRequestSidelink-r18 [0] UEInformationRequestSidelink-r18-IEs
         ,
      criticalExtensionsFuture [1] SEQUENCE {

      }
   }
}

SL-SplitQoS-InfoPC5-r18 ::= SEQUENCE {
   sl-QoS-FlowIdentity-r18 [0] SL-QoS-FlowIdentity-r16,
   sl-SplitPacketDelayBudget-r18 [1] INTEGER (0..1023)
}

UEInformationResponseSidelink-r18-IEs ::= SEQUENCE {
   sl-SplitQoS-InfoListPC5-r18 [0] SEQUENCE (SIZE (1..maxNrofSL-QFIs-r16)) OF 
      SL-SplitQoS-InfoPC5-r18 OPTIONAL, -- Need N
   lateNonCriticalExtension [1] OCTET STRING OPTIONAL,
   nonCriticalExtension [2] SEQUENCE {

   } OPTIONAL
}

-- TAG-UEINFORMATIONREQUESTSIDELINK-STOP
-- TAG-UEINFORMATIONRESPONSESIDELINK-START
UEInformationResponseSidelink-r18 ::= SEQUENCE {
   rrc-TransactionIdentifier-r18 [0] RRC-TransactionIdentifier,
   criticalExtensions [1] EXPLICIT CHOICE {
      ueInformationResponseSidelink-r18 [0] 
         UEInformationResponseSidelink-r18-IEs,
      criticalExtensionsFuture [1] SEQUENCE {

      }
   }
}

SCCH-MessageType ::= CHOICE {
   c1 [0] EXPLICIT CHOICE {
      measurementReportSidelink [0] MeasurementReportSidelink,
      rrcReconfigurationSidelink [1] RRCReconfigurationSidelink,
      rrcReconfigurationCompleteSidelink [2] RRCReconfigurationCompleteSidelink
         ,
      rrcReconfigurationFailureSidelink [3] RRCReconfigurationFailureSidelink,
      ueCapabilityEnquirySidelink [4] UECapabilityEnquirySidelink,
      ueCapabilityInformationSidelink [5] UECapabilityInformationSidelink,
      uuMessageTransferSidelink-r17 [6] UuMessageTransferSidelink-r17,
      remoteUEInformationSidelink-r17 [7] RemoteUEInformationSidelink-r17
   },
   messageClassExtension [1] EXPLICIT CHOICE {
      c2 [0] EXPLICIT CHOICE {
         notificationMessageSidelink-r17 [0] NotificationMessageSidelink-r17,
         ueAssistanceInformationSidelink-r17 [1] 
            UEAssistanceInformationSidelink-r17,
         ueInformationRequestSidelink-r18 [2] UEInformationRequestSidelink-r18,
         ueInformationResponseSidelink-r18 [3] 
            UEInformationResponseSidelink-r18,
         spare4 [4] NULL,
         spare3 [5] NULL,
         spare2 [6] NULL,
         spare1 [7] NULL
      },
      messageClassExtensionFuture-r17 [1] SEQUENCE {

      }
   }
}

-- TAG-SBCCH-SL-BCH-MESSAGE-STOP
-- TAG-SCCH-MESSAGE-START
SCCH-Message ::= SEQUENCE {
   message [0] EXPLICIT SCCH-MessageType
}

SL-MeasResultRelay-r17 ::= SEQUENCE {
   cellIdentity-r17 [0] CellAccessRelatedInfo,
   sl-RelayUE-Identity-r17 [1] SL-SourceIdentity-r17,
   sl-MeasResult-r17 [2] SL-MeasResult-r16,
   ...,
   [[
      sl-MeasQuantity-r18 [3] ENUMERATED { sl-rsrp(0), sd-rsrp(1) } OPTIONAL,
      sl-RelayIndicationMP-r18 [4] SL-RelayIndicationMP-r18 OPTIONAL
   ]]
}

SL-MeasResultListRelay-r17 ::= SEQUENCE (SIZE (1..maxNrofRelayMeas-r17)) OF SL-MeasResultRelay-r17

END
